(if (not (boundp '*VL:LAST-VERTEX-NUM*)) (setq *VL:LAST-VERTEX-NUM* nil))
(if (not (boundp '*VL:ALL-EXPORT-DATA*)) (setq *VL:ALL-EXPORT-DATA* '()))
(if (not (boundp '*VL:LAST-POLY-ENAME*)) (setq *VL:LAST-POLY-ENAME* nil))
(if (not (boundp '*VL:DIM-CHOICE*)) (setq *VL:DIM-CHOICE* nil))
(if (not (boundp '*VL:DIM-ON-LINE*)) (setq *VL:DIM-ON-LINE* nil))
(if (not (boundp '*VL:PRIV-DIM-CHOICE*)) (setq *VL:PRIV-DIM-CHOICE* nil))
(if (not (boundp '*VL:SETTINGS*)) (setq *VL:SETTINGS* nil))
;; *VL:SETTINGS* — assoc-список последних настроек COORD:
;;  number-mode, dim-mode, mline-prefix, output-mode, num-choice,
;;  start-num, continue-mode, dim-style, mline-dim-style, do-export, export-fmt, only-export
(setq *VL:TEMPLATE-DIMSTYLES* (list "Standard" "Аннотативный" "Пикетаж" "Привязки" "Привязки+выноска" "По трассе" "По трассе+выноска" "длина трубы iso" "длина сети iso" "ISO-500 пустой COORD" "ISO-500 пустой" "По зданию" "ISO-500" "деталировки" "детал_ККС"))


(setq *VL:TEMPLATE-B64*
  (list
    "QUMxMDMyAAAAAAAAA8ABAAAhAB0AAAAAAAAAAAAAAAAgAQAAAAAAAIAAAADgCQAAAA0AAAICAAD3AAAAxQAAAMUAAAAAAAAAAAAAAAAAAAAAAAAAAAAAAAAAAAAAAAAAAAAAAAAAAAAAAAAAAAAAAAAAAAAAAAAAAAAAAAAAAABoQPj3kiq17xjdC/Hxu+nr36bbPIMM"
    "PpkkXg0cBrdH3rMSTchCu4umDQNafYnwJR9d1Mv81TFFOxMNiQoc264yMJpQ7mB4Nv2SSTL23n1J3L9PFPLkgmbQa8QwtyM7oSLkIpGd4Ysf2p8ae7X4RmoElnMO2RYvZ2jU90pK0FdodlBWBwBiUmRB61JkQctSZEFrUmRBa1JkQVtccLE2WXUPAQAAAAEAAAABAAAA"
    "AQAAAAEAAAALAHUAcwBlAHIAXwBnAGUAbwAxADQAAAABAAAAAQAAAAAAAAB4ngYBnY4lAPiFUwGjjiUA+Il2AgAAAAAAAAAAAAAAAAAAAAAAAAAAAAAAAAAAAAAAAAAAAAAAAAAAAAAAAAAAAAAAAAAAAADwVgcAwVJkQctaZEHrWmRBy1JkQctSZEHqazIYLGfvNx8l"
    "bQfUNigonVfKP51EECsVBQAAAgHnAQAAUAAAAAY3AgAAsgQAAAAAAAAAAAAAAAAAAAAAAAAAAAAAAAAAAAAAAAAAAAAAAAAAAAAAAAAAAAAAAAAAAAAAAAAAAAAAAAAAAAAAAAAAAAAAAAAAAAAAAAAAAAAAiVBORw0KGgoAAAANSUhEUgAAAQAAAAB+CAMAAAD88z9R"
    "AAADAFBMVEXW1tb////W1tYAAAAAAAAAAAAAAAAAAAAAAAAAAAAAAAAAADMAAGYAAJkAAMwAAP8AMwAAMzMAM2YAM5kAM8wAM/8AZgAAZjMAZmYAZpkAZswAZv8AmQAAmTMAmWYAmZkAmcwAmf8AzAAAzDMAzGYAzJkAzMwAzP8A/wAA/zMA/2YA/5kA/8wA//8zAAAz"
    "ADMzAGYzAJkzAMwzAP8zMwAzMzMzM2YzM5kzM8wzM/8zZgAzZjMzZmYzZpkzZswzZv8zmQAzmTMzmWYzmZkzmcwzmf8zzAAzzDMzzGYzzJkzzMwzzP8z/wAz/zMz/2Yz/5kz/8wz//9mAABmADNmAGZmAJlmAMxmAP9mMwBmMzNmM2ZmM5lmM8xmM/9mZgBmZjNmZmZm"
    "ZplmZsxmZv9mmQBmmTNmmWZmmZlmmcxmmf9mzABmzDNmzGZmzJlmzMxmzP9m/wBm/zNm/2Zm/5lm/8xm//+ZAACZADOZAGaZAJmZAMyZAP+ZMwCZMzOZM2aZM5mZM8yZM/+ZZgCZZjOZZmaZZpmZZsyZZv+ZmQCZmTOZmWaZmZmZmcyZmf+ZzACZzDOZzGaZzJmZzMyZ"
    "zP+Z/wCZ/zOZ/2aZ/5mZ/8yZ///MAADMADPMAGbMAJnMAMzMAP/MMwDMMzPMM2bMM5nMM8zMM//MZgDMZjPMZmbMZpnMZszMZv/MmQDMmTPMmWbMmZnMmczMmf/MzADMzDPMzGbMzJnMzMzMzP/M/wDM/zPM/2bM/5nM/8zM////AAD/ADP/AGb/AJn/AMz/AP//MwD/"
    "MzP/M2b/M5n/M8z/M///ZgD/ZjP/Zmb/Zpn/Zsz/Zv//mQD/mTP/mWb/mZn/mcz/mf//zAD/zDP/zGb/zJn/zMz/zP///wD//zP//2b//5n//8z///8AAAANDQ0aGhooKCg1NTVDQ0NQUFBdXV1ra2t4eHiGhoaTk5OhoaGurq67u7vJycnW1tbk5OTx8fH///8AAAAA"
    "AAAAAAAAAAAAAAAAAAAAAAAAAAAAAAAAAACKYKL6AAABbUlEQVR42u3czVHDMBCAUfWh/rvSySWkAobEJCZgIyeDf3bfO0EuwIdirwTjUp7VyYej+wvDonJKtUvgAPO//18kCFAEEABSmbvjAZDlLvDaJCjAP8/XmwbonAPiBki/Ao64xUxzGba7DnEgcvLdoACTz60A"
    "AQSA7rdAjN1gFaDzPhg3wCvb4ZgroHoLwOpJUICzXwOeXtk7wLaJf5wK15IxwHvnAeu/6uXL4QJsdEdsN/cA7TgrYJ8AO66AbX/urhWQweIKEAAAW+4jTkJbfFvxAyxsg3IEaA9jhpY9QK4VcPkjQHhpA7T5AK0AAHu4/TmscyIJ+cAAAaYBqhUgQPJLogT5tueX5Mv/"
    "8wIgQK8h4GNkBPgWoOYM0P0IlcGTlADijcKph+H0m+F1AQLe+ycBavYAVkDKAOuY/4F4g1DuY2EBBJgGeO9M8JRjwTVATRzgMRCnDjBGyB3g2iB5AP8gIIAAAgAAAAAAkX0A7POKem0Y+/UAAAAASUVORK5CYILg2pL4K8nX12KoNcBiu+/UAAAAAAAAAAAAAAAAAAAA"
    "AAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAA"
    "AAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAA"
    "AAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAA"
    "AAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAA"
    "AAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAkF4HAKBaZEGrWWRBi1lkQataZEGrWmRBcNFh2OTTMQoDAAAAEABBAHAAcABJAG4AZgBvAEQA"
    "YQB0AGEATABpAHMAdAAAAAIAAAC40PAlodeTSbL6m/kob6H9cgBBAHUAdABvAGQAZQBzAGsAIABEAFcARwAuACAAIABUAGgAaQBzACAAZgBpAGwAZQAgAGkAcwAgAGEAIABUAHIAdQBzAHQAZQBkACAARABXAEcAIABsAGEAcwB0ACAAcwBhAHYAZQBkACAAYgB5ACAA"
    "YQBuACAAQQB1AHQAbwBkAGUAcwBrACAAYQBwAHAAbABpAGMAYQB0AGkAbwBuACAAbwByACAAQQB1AHQAbwBkAGUAcwBrACAAbABpAGMAZQBuAHMAZQBkACAAYQBwAHAAbABpAGMAYQB0AGkAbwBuAC4AAADo4JZRxc6yRKi/9ug7hZ1E2AA8AFAAcgBvAGQAdQBjAHQA"
    "SQBuAGYAbwByAG0AYQB0AGkAbwBuACAAbgBhAG0AZQAgAD0AXAAiAEEAdQB0AG8AQwBBAEQAXAAiACAAYgB1AGkAbABkAF8AdgBlAHIAcwBpAG8AbgA9AFwAIgBTAC4ANQAxAC4AMAAuADAAKAB4ADYANAApAFwAIgAgAHIAZQBnAGkAcwB0AHIAeQBfAHYAZQByAHMA"
    "aQBvAG4APQBcACIAMgA0AC4AMQBcACIAIABpAG4AcwB0AGEAbABsAF8AaQBkAF8AcwB0AHIAaQBuAGcAPQBcACIAQQBDAEEARAAtADUAMQAwADEAOgA0ADEAOQBcACIAIAByAGUAZwBpAHMAdAByAHkAXwBsAG8AYwBhAGwAZQBJAEQAPQBcACIAMQAwADQAOQBcACIA"
    "IABnAGkAdABfAGMAbwBtAG0AaQB0AF8AaQBkAD0AXAAiADYANwA5AGUANQAyAGEAZABhAGUANwA0ADUAYgBlAGYAMwAwADIAZQBmAGUAYwA0ADIAOAA1ADgAZQBlADgANQAzADEAMABkADkAYQA1ADkAAAAAAAAAAAAAAAAAAAAAAAAAAAAAAAAAAAAAAAAAAACwWwcA"
    "h19kQYtZZEGrWWRBi19kQYtfZEGiR+gjjkkKwVPeOB3sQyHKlhnh4hcaKmc72X/3PLvOCKBT2O3SjcXHAAAAABAAQQBwAHAASQBuAGYAbwBEAGEAdABhAEwAaQBzAHQAAAAEAAAAG9hI88wKPk26sc+B97RQswwAMgAzAC4AMAAuADIAOAAuADAALgAwAAAAuNDwJaHX"
    "k0my+pv5KG+h/XIAQQB1AHQAbwBkAGUAcwBrACAARABXAEcALgAgACAAVABoAGkAcwAgAGYAaQBsAGUAIABpAHMAIABhACAAVAByAHUAcwB0AGUAZAAgAEQAVwBHACAAbABhAHMAdAAgAHMAYQB2AGUAZAAgAGIAeQAgAGEAbgAgAEEAdQB0AG8AZABlAHMAawAgAGEA"
    "cABwAGwAaQBjAGEAdABpAG8AbgAgAG8AcgAgAEEAdQB0AG8AZABlAHMAawAgAGwAaQBjAGUAbgBzAGUAZAAgAGEAcABwAGwAaQBjAGEAdABpAG8AbgAuAAAA4IWf8vlPaBCrkQgAKyez2VEBPABwAHIAbwBwAF8AcwBlAHQAIABmAG0AdABfAGkAZAA9ACIAewBmADIA"
    "OQBmADgANQBlADAALQA0AGYAZgA5AC0AMQAwADYAOAAtAGEAYgA5ADEALQAwADgAMAAwADIAYgAyADcAYgAzAGQAOQB9ACIAPgA8AHAAcgBvAHAAIABpAGQAPQAiADgAIgA+ADwAcwB0AHIAaQBuAGcAPgB1AHMAZQByAF8AZwBlAG8AMQA0ADwALwBzAHQAcgBpAG4A"
    "ZwA+ADwALwBwAHIAbwBwAD4APABwAHIAbwBwACAAaQBkAD0AIgAxADAAIgA+ADwAZABhAHQAZQB0AGkAbQBlAD4AMgAwADIANgAtADEAMQAtADAAMgBUADEAMQA6ADIAOAA6ADQAMwA8AC8AZABhAHQAZQB0AGkAbQBlAD4APAAvAHAAcgBvAHAAPgA8AHAAcgBvAHAA"
    "IABpAGQAPQAiADIANQA4ACIAPgA8AHMAdAByAGkAbgBnAD4AQQB1AHQAbwBDAEEARAAgADIAMAAyADIAPAAvAHMAdAByAGkAbgBnAD4APAAvAHAAcgBvAHAAPgA8AHAAcgBvAHAAIABpAGQAPQAiADIANQA5ACIAPgA8AHMAdAByAGkAbgBnAD4AUwAuADUAMQAuADAA"
    "LgAwADwALwBzAHQAcgBpAG4AZwA+ADwALwBwAHIAbwBwAD4APABwAHIAbwBwACAAaQBkAD0AIgAxADIAIgA+ADwAZABhAHQAZQB0AGkAbQBlAD4AMgAwADIANgAtADEAMAAtADIANwBUADAANgA6ADEAMAA6ADUAMQA8AC8AZABhAHQAZQB0AGkAbQBlAD4APAAvAHAA"
    "cgBvAHAAPgA8AC8AcAByAG8AcABfAHMAZQB0AD4AAADo4JZRxc6yRKi/9ug7hZ1E2AA8AFAAcgBvAGQAdQBjAHQASQBuAGYAbwByAG0AYQB0AGkAbwBuACAAbgBhAG0AZQAgAD0AXAAiAEEAdQB0AG8AQwBBAEQAXAAiACAAYgB1AGkAbABkAF8AdgBlAHIAcwBpAG8A"
    "bgA9AFwAIgBTAC4ANQAxAC4AMAAuADAAKAB4ADYANAApAFwAIgAgAHIAZQBnAGkAcwB0AHIAeQBfAHYAZQByAHMAaQBvAG4APQBcACIAMgA0AC4AMQBcACIAIABpAG4AcwB0AGEAbABsAF8AaQBkAF8AcwB0AHIAaQBuAGcAPQBcACIAQQBDAEEARAAtADUAMQAwADEA"
    "OgA0ADEAOQBcACIAIAByAGUAZwBpAHMAdAByAHkAXwBsAG8AYwBhAGwAZQBJAEQAPQBcACIAMQAwADQAOQBcACIAIABnAGkAdABfAGMAbwBtAG0AaQB0AF8AaQBkAD0AXAAiADYANwA5AGUANQAyAGEAZABhAGUANwA0ADUAYgBlAGYAMwAwADIAZQBmAGUAYwA0ADIA"
    "OAA1ADgAZQBlADgANQAzADEAMABkADkAYQA1ADkAAAAAAAAAAAAAAAAAAAAAAAAAAAAAAAAAAAAAAAAAAAAAAFBEBwBmQGRBMklkQetJZEFrQGRBa0BkQRIhazCwHIvcC2phcmSAAAEACAAAAAIAcAACEgAAAIB4Ag8AYwAAAAQAAABfAAAAYgAAAGFcBVAIXAEgIgwA"
    "BqzVc2VnaWR4Xp0SBXACLokBVYAAdAcgChUABnwKA4ABAACAB7wCdAIgAAAA/BQAJvwTAgAFAACAJUwSbQQJJMwQIi4RgBB9AgAibRERfAJcCAX5fwAAkFQUnl0BcD0AAAWs1WRhdGlkeCJ8FVQQXA9cATb9EwFQBwEAAABgjAFYAT2IATt4AAWs1XNjaGlkeCKMF1wS"
    "IpwUXAGdGQxTAwAAACX5FVWIQmQFXwIgAABYP1hJbCQiDBlcBQRyAAAAAwAAbQWEJQwZXAUElgAAAAzxCmwPnBxcBVAEXBxcAiYsGlwCWFidERiNEXPAAFwIAARBY0RiX1RodW1ibmFpbF9TY2hlbWEAVAUABURzOjpUcmVhdGVkQXNPYmplY3REYXRhLYQAA0xlZ2Fj"
    "eS1QAAtJbmRleGVkUHJvcGVydC50AAxIYW5kbGVBdHRyaWJ1dGWMDjukBTRwAG9fZGF0XDFcQC79BQ5QBcxfXEZcSTIcAFgKXF9cAXRlVAK0BFVdAieUH1RVXAdcAFUUD1AChHMkLCBUBVAFfAFcC3QCnBZcb7QEVCRUMSKQHVQFAwEAAHNzcyL4HZdiSUQAtGlcYTqM"
    "BqwGdGdaA3M6YGUBYWJsZVkDYlR3LSEGADSUBThUAAWs1V9kYXRhX5zTXPVcPNzfVDWdvxSFSCJQCY0AYsAACMwGAACJUE5HDQoaWFsCDUlIRFKOS34IWFAB/PM/UVjGClBMVEXW1tb////W1taAEjEYAAANMwAAZgAAmQAAzAAA/wAzAAAzMwAzZgAzmQAzzAAz/1AH"
    "C2YzAGZmAGaZAGbMAGb/XAoLmTMAmWYAmZkAmcwAmf9YDgAOzDMAzGYAzJkAzMwAzP8A/wAA/zMA/2YA/5kA/8wA//9QFlgWB2YzAJkzAMwzAP9cGQszMzMzZjMzmTMzzDMz/1gdC2YzM2ZmM2aZM2bMM2b/VCELmTMzmWYzmZkzmcwzmf9QJQASzDMzzGYzzJkzzMwz"
    "zP8z/wAz/zMz/2Yz/5kz/8wz//9mAABmXjBmZlQpAcxmAP9UMFYaZmZcEgHMZjP/UzRmM2ZQAASZZmbMZmb/XDcLmTNmmWZmmZlmmcxmmf9aO8wzUAcACcyZZszMZsz/Zv8AZv8zZv9mZv+ZZv/MZv//mV5OM5lWR5mZXT//XEZaNGaZUC0BzJkz/1hKUh5mmVgWAcyZ"
    "Zv9UTloHZplQAAHMmZn/UlLMM1gdAAnMmZnMzJnM/5n/AJn/M5n/Zpn/mZn/zJn//8xSaTPMWmGZzFFa/1RdXU5mWA5ZQ/9TYWYzzFo0mcxRLf9eZJkzVzCZmcxZFv9aaMwzUDRcAwAEzMzM/8z/AMz/M8z/Zsz/mcz/zMz//1BwaH9UIWR0XHNgaVAlbF1Yd2hSXChk"
    "R1R7YDxYLGwwUn/MM1pKzJlQFmoW//9Waf//XDRoGgAmAA0NDRoaGigoKDU1NUNDQ1BQUF1dXWtra3h4eIaGhpOTk6Ghoa6urru7u8nJydbW1uTk5PHx8f9YKTFMC6gEAAAAAJqKYKL6AAABbUlEQVR42u3czVHDMBCAUfWh/rvSySWkAobEJCZgIyeDf3bfO0EuwIdi"
    "rwTjUp7VyYej+wvDonJKtUvgAPO//18kCFAEEABSmbvjAZDlLvDaJCjAP8/XmwbonAPiBki/Ao64xUxzGba7DnEgcvLdoACTz60AAQSA7rdAjN1gFaDzPhg3wCvb4ZgroHoLwOpJUICzXwOeXtk7wLaJf5wK15IxwHvnAeu/6uXL4QJsdEdsN/cA7TgrYJ8AO66AbX/u"
    "rhWQweIKEAAAW+4jTkJbfFvxAyxsg3IEaA9jhpY9QK4VcPkjQHhpA7T5AK0AAHu4/TmscyIJ+cAAAaYBqhUgQPJLogT5tueX5Mv/8wIgQK8h4GNkBPgWoOYM0P0IlcGTlADijcKph+H0m+F1AQLe+ycBavYAVkDKAOuY/4F4g1DuY2EBBJgGeO9M8JRjwTVATRzgMRCn"
    "DjBGyB3g2iB5AP8gIIAAAgAAAAAAkX0A7POKem0Y+/UAAAAASUVORK5CYIIAAAAAAAAAAHnACGpyY2ggANtakGRtiMCymcdnG+jVE4D0jkCcMrMegPS+WDsA2jb/YkHkB7NgwoIQlX3/7QBo4x4XK0JEk40CNgC0vlEUVfMB0FpfjwA1XQRoFwOX+4BBCWwAdPUoQHNF"
    "QHfDIFLhvgFMNwwCwCJuGBGACMAoAAAAAAANZTIBQI3GrAobomfDnwf7WtX+rDC87SHTfwSQf0gA4N2WOYVT5H8bATYA6A0AFQFIWj4UAENCERA3jlJxS6HuO0G3OEBiFGjQDWIYlP9IEvwvZIIAMBIAQgR87v8AYEUAwQa8cqAVAZC3AdU54Khu0AEQSIK/ucHcFW5r"
    "y6/henxV3SVARhLAoRsM9kClC6pZcLet0jGQ6NgHirvBbFOl7ftn/u/uRXgUOHODyb4C6QLz30bAmzIAAkvH27hBCIIgCIIgqGUevMSMSwAAgB0AMqEg5p+LAXDtD/dGs7JgafmcRzKDDoCvi+4AVBQEvCOOO4wnvzfTH4BQDZIEEAtCcW9JZtUjgFARI4n5MTmAdF9F"
    "xd3USejqKEA1AMKskFj94rE6BymhOgZBEARBw3hhAwCLFgOMlBMYsBgQp8mvDoDMigCITgHQ5ADi9Bg67gQnB/B9FCgAMJDrp0NVAog/N3hUEsxmhYVqWWdFgwxCGYD40+u7kmAyPUzFmXQyU+X+AFw2jT9fZBj4AAAAAElFTkSuQmCCcHBwcHBwOPwcIB9kAAWs1XBy"
    "dnNhdiNcQSJgECLrIAAAACr8HVgFJvwdMrxCIugtJtwsIhxBIlwiBloAAABdAAAAXFAPLjABXAQgFgwAIB+8Ay78ACL8QwFhcmNoImxFWCScMS7IApw/iEcjzC1cC5wA3AUmbCKcBJwILuwBXAOcBiAAAAAAAAAAAAAAAAAAAAAAAAAAAAAAAAAAAAAAAAAAAAAAAAAA"
    "AAAAAAAAAAAAAAAAAAAAAAAAAAAAAAAAAAAAAAAAAAAAAAAAAAAAAAAAAAAAAAAAAAAAAAAAAAAAAAAAACUcAAACAAAAAAAAAAAAAAAAAAAAAAAAAAARAAApI76E4WzW0EsHAONPZEF3T2RBK09kQetPZEHrT2RBkkv/jv1O8DAGAAAAAAAAAAABkAIgAAAAAAAAAAAA"
    "AAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAvHAAAAQAAAAAAAAAAAAAAAAAAAAAAAAARAAApI76EEEoHACxOZEEpDGRB"
    "awxkQStOZEErTmRBh03uZ1GxnEMAEMoNAABMALUEDABAakgIBCukQEYEQEZkBARAVKQEQILEBASUAAC3QJnEQJskQJyEQJ1kQJ5EQJ9EQKAkQKFkQKKkQKPEBARAs0RAtCYj5isfKULKCP8BDECAqVCFIC40YBAEcLAAAAQdSAuQAAgBYAFkAU9SAuUAJgB7ADgAQgAy"
    "AEUAQwAxADkANgAtAEQAQgBDADcALQA2ADQANAAwAC0AQgAwADgANQAtAEEAQQA0ADUAMQA5ADAANwA2ADgAMQBDAH0AokINUABQEAAAUAAAAEAAAABAAAAAAgAQAAAAAAAACAAAAAAAAAAAAAAA2AEGAQAAAQAAAAEBegEAAVgCAFMAAYGBgAGBuYAB4ZVMAABAgAAA"
    "QMAAAEEAAABBQAAAQYAAAEHAAACAAAAAgEAAAICAAACAwAAAgQAAAIFAAACBgAAAgcAAAMAAAADAQAAAwIAAAMDAAADBAAAAwUAAAMGAAADBwIAcBkAAAQCAAAEAwHAeAJgBQAABAYAAAQHAAAFAAAABQEAAAUCAAAFAwAABQQAAAUFAAAFBgAABQcAAAYAAAAGAQAAB"
    "gIAAAYDAAAGBAAABgUAAAYGAAAGBwAABwAAAAcBAAAHAgAABwMAAAcEAAAHBQAABwYAAAcHAAIAAAACAAEAAgACAAIAAwACAAQAAgAFAAIABgACAAcAAgEAAAIBAQACAQIAAgEDAAIBBAACAQUAAgEGAAIBBwHg9AAiAQACAgIAAgIDAAICBAACAgUAAgIGAAICBwGhE"
    "AAmAwEAAgMCAAIDAwACAwQAAgMFAAIDBgACAwcB4SwAIAEAAgQCAAIEAwACBAQAAgQFAAIEBgACBAcB4UgAIQEAAgUCAAIFAwACBQQAAgUFAAIFBgACBQcB4WQAJgEAAgYCAAIGAwACBgQAAgYFAAIGBgACBgcAAWGAACYHAQACBwIAAgcDAAIHBAACBwUAAgcGAAIHB"
    "wGh9AQAAQAFXPQAAwFSACwEAAUABAAGAAQABwAEAWGYACEBAAQBAgAEAQMABAEEAAQBBQAEAQYABAEHAeG0ACIBAAQCAgAEAgMABAIEAAQCBQAEAgYABAIHAaHQACgDAQAEAwIABAMDAAQDBAAEAwUABAMGAAQDBwAFYngkBAEABAQCAAQEAwAFcoAkBAUABAQGAAQEB"
    "wAFoggAIQEABAUCAAQFAwAEBQQABAUFAAQFBgAEBQcB4iQAIgEABAYCAAQGAwAEBgQABAYFAAQGBgAEBgcBokAAKAcBAAQHAgAEBwMABAcEAAQHBQAEBwYABAcHAAWiPBwBAAYAAgAGAAMBkPQKAAUABgGYAwAFolgAJQEABgECAAYBAwAGAQQABgEFAAYBBgAGAQcAB"
    "aJ0ACYBAAYCAgAGAgMABgIEAAYCBQAGAgYABgIHAAVikAAqAwEABgMCAAYDAwAGAwQABgMFAAYDBgAGAwcABaKsACQBAAYEAgAGBAMABgQEAAYEBQAGBAYABgQHAAWiyAAhAQAGBQIABgUDAAYFBAAGBQUABgUGAAYFBwHi5CoBAAYGAgAGBgMABgYFc7QRAAeH3/gFJ"
    "XElkeAb+AAH+AAAB//5oAQj+Af4B//4AAf///ioUECAANSwAUFw7YAVUYjuAAGhuYG82mABvGAH//zc8B1wYOnwAVBd8hjaIAVCLUBgtDAC8j2gXOjwJYAi8Cy+gAT58AC/AACAAJkAAACqCQBAlgAWQCi4AoICZAVMoGQFfmQFgGQFimQFlGQFlmQFmGQFmmQFnKH/t"
    "HjwAJATAgLKRFSAuNGAQBHAibSFQeGEAFiyoVIAAIdszrSYuZqkSBgGQ8Q5CVgqAAXX9TX9WAoBsElURDxJwRABhENGQEFAPXAACAAAALLhQEAbYBkPEOQlYKgZ2FQAAghCBgIAEDGwSZREPBEosATRIwICzEZASAZAAAACTEspjI1ALAUAAACEiTCMigBdQKgsmKsKY"
    "iEGQJjJHu7YqgFAMVAkFAAAZK2J5pcg3XAAFMz8G2apHgtBzCwAAAIwRNlwALnwBAA0K0AAEDQATFWFMRCDIAaffbaxw+E4EAH4CBw4PjSBUkAJUKAIAAB4H4GwZBh4H6DzIyACBIHg9CRwX/5EU96d0urf/31Lg++cuPAB6DRwXLhwABuwSdREFAw9UPYFMUZFMoMFM"
    "2jvABAYZsZLWqaA8D8BlJgCgTDdcAAOFiOlI7QAlxCmxTBk2XAAtfAHgTAUGa4OZ2FYojiARwQSxLcAELTwALqAEnwPsEoVQTAASElUOACUBQICzoVoAAIdYJSoiH+yPgAjdAgxAgQWqgIDUAgIChAAFABQEAAAUAABkPGY9gAR5SgJ4ATAVAEAlai5AAFh9VAEAV0BA"
    "AABgYGAAYG5gAHhlUwAAECAAABAwAAAQQAAAEFAAABBgAAAQcAAAIAAAACAQAAAgIAAAIDAAACBAAAAgUAAAIGAAACBwAAAwAAAAMBAAADAgAAAwMAAAMEAAADBQAAAwYAAAMHAAAGAcCBAAAEAgAABAMAAAUB4HQFAAAEBgAABAcHDRI/gwABYgAABQMAAAUEAAAFBQ"
    "AABQYAAAUHAAAGAAAABgEAAAYCAAAGAwAABgUS5QUC8AEgAAYHAAAHAAAABwEAAAcCAAAHAwAABwQAAAcFAAAHBgAABwcHgvAQAQACBkAA4wACAAQAAgAFAAIABgACAAcHg2AAgQEAAgECAAIBAwACAQQAAgEFAAIBBgACAQcHg9AAggEAAgICAAICAwACAgQAAgIFAA"
    "ICBgACAgcHhEAAgwEAAgMCAAIDAwACAwQAAgMFAAIDBgACAwcHhLAAhAEAAgQCAAIEAwACBAQAAgQFAAIEBgACBAcHhSAAhQEAAgUCAAIFAwACBQQAAgUFAAIFBgACBQcHhZAApgEAAgYCAAIGAwACBgQAAgYFAAIGBgACBgcAAgWGgACHAQACBwIAAgcDAAIHBAACBw"
    "UAAgcGAAIHBwjXsQZD0BQAAwAGx+CQBQAEAAYABAAHAAQFhmAAgQEABAECAAQBAwAEAQQABAEFAAQBBgAEAQcHhtAAggEABAICAAQCAwAEAgQABAIFAAQCBgAEAgcHh0AAgwEABAMCAAQDAwAEAwQABAMFAAQDBgAEAwcHh7AAlAEABAQCAAQEAwAEBAQABAQFAAQEBg"
    "AEBAcABoggAIUBAAQFAgAEBQMABAUEAAQFBQAEBQYABAUHB4iQAIYBAAQGAgAEBgMABAYEAAQGBQAEBgYABAYHBokAAJQHAQAEBwIABAcDAAQHBAAEBwUABAcGAAQHBweo8AEGd7YAAwZD0CYABQAGBlAHB4lgAIEBAAYBAgAGAQMABgEEAAYBBQAGAQYABgEHB4nQAI"
    "IBAAYCAgAGAgMABgIEAAYCBQAGAgYABgIHB4pAAIMBAAYDAgAGAwMABgMEAAYDBQAGAwYABgMHB4qwAKQBAAYEAgAGBAMABgQEAAYEBQAGBAYABgQHAAYFiyAAtQEABgUCAAYFAwAGBQQABgUFAAYFBgAGBQcABgYFi6AAUQAGBgIABgYDAAYGBAAGBgUAB4ff+AUlxJ"
    "X9MAf4BYAAADAH//gH+AAAB/gH+Af/+AAH///4B/IvgWOgwAP4QAIAAAAJ+AAABJ/9AEIXwBPAGIAbABpAHEAdQBlAKjgCggKgZAguZAgwZAgyhApOhApQhApehApghAg8hAg+hAhghAhihAjYhAqgofyFU1AJUCDECBM6qghFQBUAQIqAEQAouAKFwQAByZ5kCkpkCk"
    "xkCk5kClBkClJkClRkClZkClhkCaCh//VzoAQgHAgUohQAEIAAAAJXgiAARwH4AAIdDTuCHRQLEhADytcofu50FAInwoAAYAAA6D+pMFaUgJIUgQW7ADfABOCwCBSmE1+wBCsRWoDwBMqWqUFQEp4qPKZ1W8D842NKpxWqBUBAVUEoK0GncEOihWIqAHla5Q/dzoKBUc"
    "bGlU4rVAqAU8VHlM6reB/IKYgBgAFwAYABgALQBwVtSAkhSAkxQ/r3QuACkGwIFKoSK0SjP9Ag1wIAqnRUC5grikBI80tS4AaQzhN8gAiDxoDAO6pASPaK96DEshPsgACOdBQLmCvKQEj1nXI7MogTQhI7AoBSBKIh+lwDUAaGkBNmqghC6YBgAQm0ZApaZApcZApeZA"
    "pgZApiZApkZApmZApoZAm2ofINwqAFlpTJAgAYAAIeDoZwSnQEC6kwVde2Uo+3JpZUyYZZRzq2OnQEDoYwXM7PEbFJkQBDE4BgnU6AgVGdniNikyIAi7YxiAF2BjBCUAcFYUgJJjY+qvJmZWTKGISZodQLHQYQOypASPEl6ICpBhuArQXwO0pASPFMt5Ck3MPvimCKdA"
    "QLmCtqQEj9SMcl024aBdCqtEKQC1AQxAgTkqoIIu0AUAApymQKamQKbGQKbmQKcGQJzKH4bBcRtOwBsAB9LbyW+y6WkNANr5ekpTajZAuYKopASPQp9xGzkkODBWeJmEghs66jCwAQACnYZApyZAp0ZAp2ZAp4ZAnaofh0txG0/AGwAH0FOnYy5TWR0AF1aMmb0BOEC5"
    "gqKkBI8K93IbO2GkNgKXACwAzVQ2BDyqoILUAVDk/QAFnmZAp6ZAp8ZAp+ZAqAZAqCZAnoof8OZ9G1DMGwPSUXAi7JNcGwwgSz7QGzVAuYKcpASPAGqJCmG4crgKDMMNrNW9NEC5gp6kBI+dRnkmPba6i1yOQT6qMBwEAAKfZkC3BkC3JkC3RkC3ZkCfih+lqHEbbsCD"
    "AALSU6BryHlxHQAX5wVlftQxQLmDgl2NfnEbP7AbAoDkMgD9XEEBQGqggy4cBAAMoEZAqMZAqOZAqQZAqSZAqUZAqWZAqYZAoGofVO+FYclSwMkN0e3EW/I40RUAsggTjfD7LPDJCMI9d43t8LCkBAUgIsgzBwAAB6H8ZGRkYQAiCBMABz24i35HGiKgFkECcb4fZYgV"
    "BHrvG9vhYUiszAODJgAWgBlszQMbgDUAcFKezWyMJHkRUszNABDRVBG9V9e1HQCuEe3ybHgmQANPYYSH+JqQOYKSpASPXoMuadpS2EwMEmO+DSclHQCOVWvRYpMsyAwDlKQEj0xUdVlTxn/QDokMXogMBbmClqQEj5rddVlAvtEfDYZZQuowlAUADaGGQKmmQKnGQKnm"
    "QKoGQKomQKpGQKpmQKGqH+ZpMgAi5hJUISWEGND6BJwiLH4U1kYqYRkVJAYTw4xxK1TMn4D9KigRA4ykBI+KtYgKxE+ICiooEQOOpASPutCICsRNqAqQIwW5gpCkBI/kenlAQ7DcAhehLwDlUJoBRWqggy4oEQAIosZAowZAoyZAo0ZAo2ZAo4ZAo6ZAouofunh5HEYw"
    "yAHQMgMMpASPHrd5CkfQaCyQFyIMGwMOpASPAhKICjB4BA8hAHzurUY8ZERAuYIQpASPqnZxMkW+cg7BiedHMXgOAAKj5kCkJkCkRkCkZkCkhkCkCh8d0XEbSTdcAgInQ0C5glowZYdxG0i65zBRgRtmMbABAAKzZkC2BkC2JkC2RkC2ZkCzih8bi33CbJxLJKREAAws"
    "oAAAIdFh1Rh0ueVVAJ8jWtc9eTxAuYIypASPr7lxHWeyHauFgh1oajAAEgACtEZAtoZAtqZAtsZAtuZAtGofG7lxHW0y0AELVsvIooqFVQA9FkV3RmsiqBkDLKQEj35ycR1ouFUJnq2DAO0FDEBH6ICNIhwSAIgwqAE0AbwBkAGUAbABfAFMAcABhAGMAZQCs4AoICZA"
    "K6oGJAZAloZAlqZAlwZAlyZAl0ZAl6ZAl8ZAl+ZAmAZAmCZAmEZAmGZAmIZAmKZAmMZAmOZAmQZAmSZAmUZAmWZAmYZAmaZAsgZAsiZAskZAssZAsuYkKiRfUzpJADEAQIEuJUg6AACCP8UNgdQPdVMQBxiboldF0NAwbFQNDwP0OSQBTAE8AIAA1ADAACLYcwAU/BEM"
    "EQQRCBD4EOQTqAKkBJCkBJdwXk0ANRNAgS5kgNoAAIdkGNMjWCgAAQ0A8rXKH7qdFQDPK1yh+5nREAxTBLidDXMEudBQYAQAIrqdAQDd1rlDt3PPkAhAl4pASR8qoKEAfAVAgS6R9REgAGAEQAUwBUAFkATABFAAIARowAIkhFMEDwPwIBkgJiLAEAcKTTuCHRQrEVAP"
    "XBoFidDQILpWQVAigE0BAAAAJCL8Smg0kAEAEAGncEOigWIaAHla5Q/dToqBBp3BDooFiQgB5WuUP3U6KgQjwCkBFiQgByLAKQAOxOhoFUBAFCBLwyBLtSAkhSBHFSBR73mrogBMBUCBL1EgAZUCVnQeJNgs8yu50FAgLLACIncsQEAVaCkFJSBM7yslPwBQewIvpUg6"
    "AFB7CypxqTw6ExAPC92H4HYQIrxOAAgAAAAPA/QkfBD4EIAA3BDQEMAQ9BDgETgSaIt4mpI7fRDljRANcIwENRTPZwuRUSLMUX0QHeKMAeiPDyP4kmpKMBEgAqgEMD8HqdAQaUgVdFG0ASAOHAcipCqYRgRFIE2f5K5DajUwZYg1CxAYpVR3kxA3LSe0JerQuDUABSxQ"
    "ENQRCBDAEOwQ4BEAEPgQyBDoEOASmDcGsgOaAEgFAIEwIAK9ClZoNw99FdvSCoeQ0A3McPrDys7QIKpoqwTgfyk8Ndc/sDh0AgAxBbeS32XS0hoBtfL0lKbUbIEe3kEOigWIaAHq/yh27nnyBHort6QVDyGgF512qSPl56gQDAQBUgJIUgJOUgTkOUM7AFWAMC30BgQd"
    "zosL9sYPuDkDHHwQ4BDoijrYEZg3B6+1dwBIBYCBMSUibCkIQCkU7UoQWgFGQBclBCoKgqlZBUBQATA0E7P4dXQsxAEALhKH6ul24siIALt4jRFgSboECnTsZcprI6AC7eI0RYEm6BAp07GXKayOgAurRkzegJwgVAQBUgJIUgJPUgTr7OCNHmV8HgaUdheJmHVFQBcl"
    "iCl8HgQAwh49hBCNxB14AgAEEpIEyuGCqGgAuQJZ9oDZqgRKLgRdklweAAbkCWfaA2aoESi4EXZJrI6AC+GG1mremiCcHgRQUgTyQmk9aYcxlM6EvQUl2QfowLJN0CLYXGTOCSB8EQAQ4BDIETwQ3GGGKI+9S7hNdBAt5AUEJdZZNR02TbVeQC0EAQABEKwAyBEsEPQQ"
    "+BEEEOgQwBAoBiSyFUBOfUMynGIE2OqcFXRFQCYULHxDBANyS2j6aIFwQcQBACAShi7HceaoaAC8xDu80TmKBEp0DXkPLiOgAvMQ7vNE5igRKdA15Dy4joAL84Kyv2oYoJxDA1FSBPoH2SQlETKYywsIPq8kfVMQHfetAU6FzC4kEQkBCBEAEMARBBEEENQnJxFGRYdu"
    "kjKlfHMNNDgK++0ERkBuduAg7VwrQGwvBFIh/CnBQhwiJG7ALwA0AAAACoCN6r69qOgFcI9vk2PBMgAaewwkP8TUgEJMd8Gk5KOgEcqteixSZYgAaewwkP8TUgAHMd8Gk5KOgC8qteixSZYgVIzFBFJSBQH4iE9lZzKEZw3VDNePQTTTEAulBWJZCMqQrXdEI2QU3DMv"
    "fQZojmcGtn1nM4xnBbS0qZgivEpAJvAobDcj03EBAj3zNwAAACQaGohoNBgaAAHU6KgQadwQ6KBYkIBOERY/CmsjnKsFBHVSBQt6GUttMzOMZwzNID8xnvnTEAcF/SVdoBG+MzzQj/jsENQnOBMHwBCAAGgQaBCEE5/9saVBbhNkJSR4FAzHMltqRKsVkBOJI6MFVlC2"
    "ryjQImAUBRD0EMAQgAEEbhbgEiZ6IEciJJEVZIQlDMc4LeAO4ZWQJxOk0l6rT7URLNQRBggRABEMEMQRLCeSFbsGhCOE4wznL+zXMlaVUCOO4TsDhJG8EQACKFAQbBC8EIAAiBCAEEAQhBCEEKynI9Kkf2+fZaVYdF8ABLKAAACHQCl9QeA/5HlUQH9QQavuhDx8oQVT"
    "4MIoWzaohXQKxAEAIAuaSCkgKGpoAN0h6r+bKdoEXgWaOCi8KqATdozf4emHaBCw6ow6XPKqgE+RrWuevJ4gbNEGSVICU1IFmuZBjSDl/CAMSkAptl2oVEDeQZXaNHNAfCAEUiF3x6ldvDAsDwAgB4A78+MSamgAcQVFlkEqAgReQq/KeVAqoAnY881BoqgIEKtl5FFF"
    "QqqAHosiu6M1oCCcIAlUUgWh3m0LABUBQEgjWBUKSiIfOgsuAE0MQFYqgSLgMgowqAFAAYQBwAGUAcgBLmQqACIqBitGK2orP3CTGACVAQyAQKhBSAZAMcQiBEBI5EBJBEBJJECsX0A+OwBRDMCBWJBlICVgbE4AawQVSAlpHAAAAAKpkIBAAAwwBBz8EPgQ0BD8EOAR"
    "BBDgEegCggSgoh6jMKIsoWr2GgClAQ0AQOpByAQiJDuEQElEQElkQEmEQEmkQFxfd01ZABsNQICTUgURIADABBAHIAaQBhAGwAIABOAGEAcgByAG8AdwBHIgAAAKomAAZCAASQPQ/QVQAC0AMQAzADEAQpBAFIASQBBAEwATgAuAFQAVABGAIGAaCBqHvhpjABsNQIC4"
    "kmURIADwBUAGkAbQBlAHMAIABOAGUAdwAgAFIAbwBtAGEAbgBHEgAACsGAAWABEBCBwEGAQfBF8AEwQeBCEEIgRCXQAaQBtAGUAcwAuAHQAdABmAImwZAACXrewNAD0OAEFqQEgEIsYihiK/gFIIABUPAEGqQEgEH6SkBgAND4BB6ogftYQJAB0QAEIqQEgEMp8kWj4A"
    "xQMQgEJqRQgEIkQ7pDvEO+Q8BEAg5EA0xEBKxEBK5EBLBEBLJEBLREBLZEBcZEBchEBcpEBcxEBc5EBqBECO3z20KwAbEMCAQeqAEPQQBDAEEARABfAE0ATABFAEEARABFAFIAVgBFAFIA+gCghKh1EeMQAbEMCAaaqAESQQBDAEEARABfAE4AQQBWAF8AVgBDAEQASQ"
    "BTAFAATABBAFkAKgGghKh9YNMQAbEMCAlaqAESQQBjAEEAZQBjAEwAYQB5AGUAcgBTAHQAYQBuAGQAYQByAGQAKgGghKh7TKIQAbEMCAleqAEKQQBDAEEARABfAFAAUwBFAFgAVACqAKCEqHiz81ABsQwICWKoARRBAEMAQQBEAF8ARABTAFQAWQBMAEUAXwBEAEkATQ"
    "BCAFIARQBBAEsASgGghKh++fEwAbEMCAlmqAEDQQBEAEUAOgCghKh1rWLQAbEMCAlqqAEQQQBjAEMAbQBUAHIFh5DwcwBwAGEAcgBlAG4AYwB5AAoF83gik9bDcEluqAEYQQBJVRQCjIMgkF8ARABJAE0AVABFBcLggF8ARgBJAEwATACGcQwUktZxC46oB8HAAEQAYg"
    "BCAGwAbwBjAGsAUgBlAHAARQBVVJcH8cAyg9Zgy5Kl8cBjAEVAwKQAeQBuAGEAbQBpAGMMwPBUAHIAdQBlAEfQZQfxyzQDV1EGpUTjwEAQYEcAVQBJAEQARmK3ntdiu5qjm1AiDXK+obJ3waAeqAENRkSAALBVAFQASABFAE4AVgBJAFIATwBOANoAoISoez6xtsCgAB"
    "1CqAEHQQBjAGEAZABfAFQAQwB28Hj3lXXAcDgR2qgBJUbBJchSqAOJRbBwSgBPAEcARwBFBkCHQDAhAE4ARwIhg5BgXwBTAFkATQBFweAE/ABaAqCEqHOuxAAM0DEQBCqkPBSAQk5DwkQEnEQEnkQEoEQEokQEpEQEpkQEqEQEqkQI4kQI5EQI5kQI6EQI6qQEqKJOpA"
    "SmpASqo8PxKm4gCQARFAgJRQxSAlhGhwEoAAI+wRBeQEMUd9GhAEJJBkAAUD4P0GUeBGiAFGAACQGkzczMzMzM7D8FgBAAzMz0z8UrgehetR2D8mpmZmZmZ2T+qQYLURU+yHpP0i7KkMDBAA6pArXo3A9Crc/hmZUAABjlAZDGAPBvTP4gQQAAABgiIKpxggWAIKgAEg"
    "SBIEgVIEl1aA1SI0tiKFk2VgJQALAABZQD+/z+/yEj4IfAhAAIQIgAhgCIIIgghqCIIiOFIAAh4AHwBV1AFBCkIEyFBSAkxSAjNQYAACy/vPAKBtOZAgCZ4Daqq8MQABj/AADDAD0BQGmh1hkKhUCikP2aUwBlgtMAQDBNIElyAxIRU1CQMiMAgDClYAZAiWCHoIfAiC"
    "CHRQNps0VNQDWTTKeDQBMFICMHI1kfiANQzSNSAltGeAFGAQBGeQEEEjKJkjno4ADHgBeE85TgdialtuZqT+f3BqT+KQBLxABoAAAAwQAdBKmqBxoAsuEQeCIAIQBwceaAh2CHAIeghgiHIAAYYIYgiWCEAA0gDmAN4AgiYAHoBSdFSUVj8Fli30AwLyJf4Aplp0lRAu"
    "SAcLjUgJbRngBRgEARnkBBAiQYMAJL2SA3gBdEMFAQxR30aEASh0Awz4P0GUeBGiAFGAACQGmJpUqQKZqT+JqVMCmpP4kAQGpBgtRFT7Iek/IjSRBAMEAHQSpoZkTgFjlAZJkQuBWRlgIlq9Bgh4AlS0BCBUgSXVoDUl4jEAWSWcRwA0FlAP7/P7/IcaAh2CHAIeghgC"
    "EAAgghqCIQIcAhAANIA5gDeAVXkAUEKQgWXUFICTFICMFICMFBQUFBQ/sLHzAHgRQICVUC4IBDb1DqqFHUR3PQOQ/HECDo4FPQ8v8w7kBoyQ/H4KEQKswHAEATkP4gctDAyAgAHSBJdXMggMC0eP7/IokgCmAJ4AWgBqI2SMAA1AAH4IhgiCCIQIfAhyCEAAhgCeAJ4A"
    "pACIAVSkA0EKVX9QlL4IBKzqAJABEUCBHFAgB+IDkBqEOCAC5QP+ZboAIDfhAxw54wMJVeQj+RK67DsCkFDEAKJsOwOQxR30aEAllBYLD4P0GUeBGiAFGAACQGl+YjoPJR6nOQB8rA/ZP6pBgtRFT7Iek/oAAAAwQAO4QggIdYZCoVAopD9kM2AABdM/iBxAAAAGaMsi"
    "uJZYAgqBIEgSB0gSXIDEhFUDchkFlHwBACYBZQD//z+/yEj4IfAhAAG4IaAhgCHoIcAicCVVEAUEKQgS9UFICTFICMFIEFlBQUFBQ36N3gCYAVVu0CA85AZz7p8T8HAqIAPICiXgGQPSBJdRIRQx1BYC/8/v8g7rbgFVBGBrArVQUgJLcKcGURVQUPCZ8ACWVWsdL2QS"
    "BTFIEdkaAASgJH4c5P04CBKFWOQleU0DJTevD0P6JQgSCPk/oAAAAwQAOQGkfDgIBECHWGQqFQKKQ/Ik7hbk/ni8Ag5D+IHEIlCjKUUSACOQHQUgdIElyAxIRSU4Oi5PEoWaAiIdEhgjZBIJIAIfAhkCHQIcAlVhIzYSMBQimHwBFIEFlCIwEgM/H7rdALBkPSAQTw4O"
    "g/R6MA5AJEQZKQghj+LQFAaEQLhyJLuuBZQJJyceB5AAI1DPAQAAGAAiQBICgAFSBIEkHB42RAcAAxJoCGoIhAhgCHYIvgA0CDQIQglVRGV1zFR1IsQRAChSAjBSBBZQUFB/tHgCyQIKgEMqRFAQBHkEAQwBBAEQAXwBDAEkAUABfAFAAUgBFAFYASQBPAFUAUwBdAQA"
    "QzwBEAFUAQwBUAF8ASQBOAEYATwBCkEAQwBBAEQAXwBDAE8ATABPAFIARRBAEMAQQBEAF8ARABFAFQAQQBJAEwAVgBJAEUAVwBTAFQAWQBMAEUAQ5BAn7C4idC4EUATABEAEwCM/M0AEKbAmARwBSAFbIkABC7AcDEwAQQBZAE8AVQBUAENQQJgcBBNAEEAVABEnljkR"
    "FCjJKtAiGioEECWZNTAmfmMEPbsaNAEwZDcKFAFMAVABZAEwARQBEbEdUGw4AAJUAFMARQBUAFQASQBOAEcAUwBEkKAgBhQAEwATwBUAFKw5BROAEEATQBFAzjsFMGQ+ItQ3nTtVsyFMARRgWlJgOAFTYhQBXMEkD7AkDFQAQQBCAEwARQBTAFQAWWUCRLBgU10UwBUj"
    "vD2wJMxEBwVwBJAFAARQBPAigTAFIkg5BBAFIAUwBFlYIwwQAQgBWAEEAUgBJAEEAQhnQxABJMAnXAYAKmQAqEqARANKQuZEA1ZEBk5CGkI0QuRDrkIuQjJCHENsRANQQwxDMkQGUkQKx52jNwBVCoBGpAZA0BAEFSgwbgAUBRsEOARBBEIEMQBBRsEOARBBEIEMgAOA"
    "aCGIIYQkRCskK99AMEFeDlykbA4AGh0IAeQBCAGwAbwBjAGsAQdCAHkATABhAHkAZQByAEGRwBsAG8AYgBhAGwAXdBEMMuQyxDMfvJ9IAF0KgHXkZxENNAFUvQAaCFMAdABhAG4AZABhAHIAZABDBAEPQQ9BD4EQgQwBEIEOAQyBD0ESwQ5BI4BkJAA3QF0EOwQ8v6+K"
    "IgAxCoBF5AZAUBAEIUwB0AGEAbgBkAGEAcgBkAIoA4IWghhCMTffDAAjCoBGZAaQEAIIYghn8AIgAEFBAEOkBlwNABoZOAG8AcgBtAGEAbABqAOCBIIYQh6iH0MaHgGxBgqAbaQGSFAQBAkEAMABAiNETguQQAyAECQQAzAECQQA0FAFAzUAQJBADWEFcFEF4FAFAAQ5"
    "AECQgAwAECQgAxAECQgAyAECQgAzUQUNYQVQUQXYUQU3UQUOYAUBkAQJDFAaIwpRkMBRGjBRGgxSGkMAURrAUxowA3BUCgfgAQJDADkAQJEAURpAUBoAZxAAyAGoFoIYghhDbkQCSEQCSkQCTEQCTkQCUEQCUkQCVEQCVkQCWEQCWkQCXEQCXkQCYEQCYkQCZEQCZkQC"
    "aEQCakQCbEQCbkQCcEQCckQCdEQCdkQCeEQCekQCfEQCfkQCgEQCgkQChEQChxhuHQAmQsCASeQGkAAj/BUACIEAgZiAHQAcAB0AcFxQbb8VWx8AJkLAgEokJvAVAAKRAIIYgB0AGIAYACUAcFyQbb955o0IZJ0IwZ0IG2wIAtBtv4PsjQiknQjRfggZAGwRA10Qbb+T"
    "TYwIpSP5jAh8GgJdUG2/4o0aS54jARF9CBqMEQKQbb9j3n0RS54jASWMCIwRA9Btv9XjIW01S5wjAQFlAIJUPlw1I0SeBF4Qbb+vLx12CeQGJAR3AwAEBIGZAFQ/Bh0AcF5Qbb+2/3YITCSECAIBBASBmqQIApBtv/XQhQhkhAgCAgQEgZykCALQbb9b534rTKSXCEQE"
    "glwhXBkGJQBwXxBtv95sfStMlCIGBZQEgpiAGAAYZBIHLQBwX1Btv1Z5O20rTZYjCAMl9CMAGKEAhxiAF4AYgBkAHAARABAAHoAQABiAE4AWgBgAEQB1AHBfkG2/BP05AFV7TZ0qCbwPBYaYgBeAGwAaMfQABm0AcF/Qbb9Le4QPnTEKLfcAGYAZNPUAYF1aTYQPlTgL"
    "LfcAGIAbNfQAAlBtv2OrdQ9Olj4Lg6Q+AoaZgBeAOOwBA5Btv5rmN21NTp09DMweXE0yzAQGZQBwYNBtv3okhB6VPQwt5AE33AIDYRBtv5cJhB6VPQ0t5AEyvAUGZQBwYVBtv0/RfQ5PnTwNxB4BGYAXgDXUAgNhkG2/XN2MDpU8Di3cATKkBlwdAtBtv3PLjA6VPA4t"
    "3AE1zAIEYhBtv+wTK2VaT6z4AqEAhRiAMEQKBlUAcGJQbb/x4nW0UJ04D74ahxhUr1x2MVwIB3UAcGKQbb+nXjNtG1CeOQCEI5wTAwAAoQCFGTXcAQLQbb8ThowNnTgBzA0yHAoGVQBwYxBtvyP+dYNQnXMCvg2GmKzbLvwNAAhtAHBjUG2/7ms9AFcKgIBqJAZAkBAE"
    "KSQBtCVNY6QidBsAFADIANABCE0AZQB0AHIAaQBjADUAMAA0AaCGIIYRANURAS7/iPEiIkodYaQ1SR0CI2AZADoP3oo7AvkDCoBmZAZGUBAELMgBkAFcAaQByAGUAZgByAGEAbQBlAELMwBkAFcAaQByAGUAZgByAGEAbQBlAEFQgBhAHMAaQBjAEIQgIxhjAnAGgAdA"
    "IpxZAgQtDAG8I1ghAsgBDAGgIzwfAAmcAZQBCkMAbwBuAGMAZQBwAHQAdQBhAGwAQNEjlGEKEMRQBkAGcAZQBDAG8CIYWQgHIATwBmAGYAQtGCSAkSOjkdAB0CN4ZwAHuAEERgBsAGEAdABDUYAbABhAHQAVwBpAHSJsEgJAGQAZwCLYYgAEEHRwBvAHUAcgBhAHUAZA"
    "BEEcAbwB1Gk21IA7BdABoAEUAZABXCcPzAEGSABpAGQAZABlAG4AQlKAUBQNHQAZQByAE8AZgBmAELTABiLBWlAjUV1AWDsGByAG4AQtPAHYbSWggDsHPAGYAZgBCVIAZWA5AmkAcwB0YGsDQZTAGgAYVCgFQBkAERUwBoAitFgNBlAGQAIAB3AGkAdABoACAFwDUEMC"
    "BzAEOUxkUCK8lQjMAIABvAGYAIABHGwwA+QBB1MAa2SCAAVjAGgAeQBB1QAaABpAGMAawBlAG4AQlVAUIulfYFhAIixoCwQVYAC0AUgBhAHkAig+bIEAST5EBLhDPENKQ1JDRENIRALqQ1BDNEM2QzhDOkNCRALmQ05EAuhDRkQDBEQDAkQC/EQC/kNMQ0BEAwEo2+cA"
    "JUKAamQGRBAqBICgSAoGgMgIZmZmZmZnxn6AgABU2QACB8gIDEBAQGEAICgKAoIgMA4AAYYTrAgAAgZAAgKAoCgKAqAoQgMQEBAYQAgKXAMAOgyAoEgMA4AAYYAgKCoDIDICQFAUBkBkBIDQGgJASAkBICQEgKZIDICoDIDAAAAGEAICmSAoGgMf4AAYQAgJAUyQFMkB"
    "TJASApkgMAAiFDgHMgSAoCQFQFQFC1ifBmwAbwByAEMAaCOsKglnAGUAQ9zAHQAcgBtgTQUcwBfAG8AZwCTIawAOGkAZgC0AeCIIMz8VFO0AJUKAaKQGQlAiBoCgSAoCgMgyrAMHf///4QAgKBICgTKsA1RECgAAIiAgKEIDAOAAGGAwzQMaICvMAzPIDT3EAwcpAHgh"
    "KDM/X5XfVDwCaSQGQtB0dzzEAzl0BzWkA5R3ImxUAgAAAEnAICOUBwMDRABpAG0+VAcHDQB4IWgzP6Avzlw4CIBdZAZFkCoFIFVQIxNXZ8Z/c2oHyBRscwFIDIJQUa4BIlRMBUAEgMgMyEIFZDUDEyAyDSBUaKsDSC1UkBqoICCYCgIMRQBkAGOmAG8AeKsCTwBmAGY+"
    "SAMGMQBoMygzPzPYc+UkBkMgPtgGICVTDkYAYSVEGCIxF3Qj6TluPqwDDy0AeCHoMz+sIdYAHUKAZqQGkFSoAygKAoCgSDhSDjIDMkgOIvgRaHIwKA6BqNQgJKQDKMAaPMARBhEAcAgzP60r6lWmZiJYPCADbgMoCjRxAzIiqlYZACA+bQMNJjAeIqAgAXQAaACdsHM+"
    "JAcHNQB4IEgzPyvL3Vk7ZyLMI1g7IngVIBIpBzI2UBUgLCQHBAdHAG8AdQAiKSR1IqBDPDwHBx0AeCBoMz9wmfBnOGQGQKzlOoQDIF1BBxD4OCAQWAcHAQC4IIgzP/Yw5FA9A2hkBkGQIlLnCgQgDtUcgSLYICQzFiIgIDc0CyAs0BwrFCg9sBwHGQB4IQgzP78/yFA6"
    "A4Bc5AZFECANIRlSIDcgGQQJSgBpAHQAJEgVIAQJGSUkChk69yMIGQFp5AZDI1wVUOM6rCMw5B8Bg6AoOiNcJzxgFSAmXCcCTABpAG4jUDEgDggZA8gzP7uOzGBuAl0kBkVQIA3hBkogN+AGAQtPAHYjHBwmkCogBPEGLXNvWlvhUDQHaOQGQhAiBICgaCI8LSAUThwA"
    "ADLcGITaICVMHDGAND28DQclAHghSDM/Nd7eVDkDgGCkBkbQWDlcqDo5FTI47TEALaMDPDw8IrQygTpUICTyHwZTI8QxImE5ZD5JHBlzcgDU9Xg4AWQGRpAgA4oDKAovzDEj9BQjgCMtjAMjwiogKCAsjQMR3zggAHcj9BECaAAgAGUlQCs/MyAFAKgiCyu6F/ZkPgFf"
    "pAZFgHc1YDkjcC4ssDUBOAAGGCVgOSfYGCBGsTUOsEAIcwAgAG8AZgAgAEcjnSB5PtEHOXN9MuroeD4B5AZGECAPxBwz6QNaNkkkMiArnDktIEI9EQ8dcjuO+ySEOQGkBkNQJtAnIA2cGSK8QAECoChiNowDJdgnICWcGQEHVABoIwxHIshFP4gyBx0AeCGoMz/0lOBQ"
    "dANoJAZBUCQiZEM7/CMwJB10OCBF3SMJIpgnLJhPPSAHByUAeCDoMz+n+dxQOQOAYCQGRlAnqRIoEuwFAgAAAcB+KShIhOw1tDI/oA4gJdgZAwVYAC0AUiOkcz2BAxV0qgAazeULACVJwIDKZAaIIYghn8Jh3QKtBQqAgVjkBkbQIARUjAFIARQBWAEMATAjoH0DEAEE"
    "AUABIh+APAFgI/13DCPsdwAGOAEOQQBOAE4ATwBBAEwATABWAEkAUwBJJQh6CkKQwBBAE4ATgBPAFMAiQX4TI5R/AAEwBFAFQAUgBBAE4AUwBQAEEAUgIh2qBCI3qDUMASLJfRQjC4IUAUgpl3sLQwA0dXvAIlR7ARFAFcAqeIEqdnswBSM4gQYFcAUwBFAEMAUiKbDw"
    "Yh9ABSITsFAEHSIVezSAHQAUDAEIRABJAE0AQQBTAFMATwBDAEQRQBYAFAATwBSAFQAUABBAFAAiSoEUwFwCAxDAEUAQlGkYBCLEggALUAVgBBAEwAQhIAEkARABFAFQARQBYAFQAQdIAFApYIQHQlIAFAASQBOAEiV8ggQVABDkgAUAN3EEISKchVEUYCPHfTABCSTR"
    "g0UiloUAVmxgBELTABBAFkBUJ1xdDhUAEkARgBZAENTABJAEcASAYT/gIzyxBuAEkAVABTAEMS7EBSIAiCKggwQJTQBTAEwAIniDIliHIleBQhPAU3ERgBQmEIMFhQAEQARgBGBgdAXQBFAEJUwBPCPWhBABUEAi3YQIVFEEUgBUAEUATngTARXAEkBfUBPAFSJ4hqsT"
    "N4ToInx/AExArIRArKRArMRArORArQRArSRArURArWRArYRAraRArcRAreRArgRAriRArkRArmRAroRArqRArsRAruRArwRAryRAr0RAr2RAr4RAr6RAr9+TIyAALUHAgVokBgBCXIZQpgACEQAQQBSAEQAigDggqECsf+WRIABhCWQ1kAAEyECsf0URJHAJBqQGAEKS"
    "QBtAHCNEXQACGkAYQBsADIANACqAOCDoQKx/lUOBCuQ4oAAFIQhArH+6gxJkFA5bJAYAQEwABoA4IShArH/cy4kFZFkFgFgFA0hArH/ijYkFpFkFQFgFBGhArH95iBRwEQ/kBgBAjMAMQAqAOCGIQKx/5ql9C1xkF2wLXzqDyh5sCwRcZAYAQdCAIgSOnI0BHoA4IVY6"
    "tiaEDmQabCVeNSaJdRpcVxqNwA1VGiJeMZVefQtdZBpdCyJeMR7JiAVsMWgFXjFBSYgFpRciXTGKmAVVF0xVPSJWMZ3PeGYIXiQGAEIMQAuADAC0AAEigDgiXjSdZXkUXmQaWToiXjEaS4gFZBpoFF4xgU6IBWQaVQsjVTGaiV1fZDFoBVcxkMsWbUtfXBYHzEAMgA3A"
    "DoA4I1Yy7P9xEl9sF1E4I1YyNYgjOs9XaiAEOM8L5iwKK9+PySIAVQxAgIwkC9AVfAEiIIgCuAGUApcUtCEJRiZARkofelMwAJ0BXwnqgIEiFfsdEnAiIqTQBLgAzADAAp+ACw2GQEamQEbGQEbmQEcKH2OpIzb8gI4iCP4GgxggqiIfLqSlIgCNBYCpqkDQEBRJIoiP"
    "JOiXCxQBOAEgAQQBOAEMARQBItiPBzABPAEMASwBDUEniJcuUA8ESdBAGMARACLrcx5AGyKhjUAi92YQgBsi4I0ACcAawBSAG8AdQBuAGQAVAByAGkAcABQAHUAcgCJ4awUUAByAGUAdgCKkZySMagAEH4EwBEBU5EBXpEBX3/xyFQAjAQCAryMp/1AS6FMNAqAOCNKI"
    "hwTgbwBQAMCAsBdRUSAQAYxMAAYACESAACHf/4Jv6vEkEHQIfFDLMf2wJAwjLC0AFAPA/AAGAIAiKwAHoAQACSANwA5gDKAOQA6ADSAN4A3ACgAN4A0gXHkPCArABGwDwRsyAsFREFICTC4yfRyxF1xOIpziI0rhAACMHA30jOrXqRXAdAZMVlj1AX8TJEiyrRwgIAHN"
    "AchcHAEgMgLGbBwGq14gABsBAIEFdEAIhfAE8AYgBsAGkAciNHAAA1AIoAwCiIf+Hi8AJgTAgQYhUoAAhySbwxwX+Go7BwGNAQUUNF8HAcB/sECURD95H2+FgQZhIjjoBVggaiIfUmYYbRozfBoGQqAEQAMQA4AEbBgGDVE2ACwEwIFJFlAWZhcAcBI9KtklUP8HB1xo"
    "0MEzsIiAeSJw/wjOgoBsFXUgJI/SQIsOoUABIjklAjDoAAZCB3VPUw4PAIzIDgSFICSPhZFCE5ISSeEw6QDQFAYODQAQBxUs8CNEqgSEJQKTBWVIEzYs0oR1NjYTRSBQhTaQdzZHCi5lNksQAskO6ZQ0A2y/AE2NroQ0CE6AgGwVRSAkjzFBiAwQAmQTiAwEQgdk+SOD"
    "tZQyaAwDVSAkj0nvFLkVSxYkCxABoCiEMAGnQECwtS5Zdi4z0nUuOWhpdy4gAwB0LgFt7IQAEpEvTcQuAAnT0V29IKh5DQA3McPrDys7QKkB1wUMyamkTxoQApAvBc/acr3/VABkE1QpCIDrgoZk1NInjHorJCz7DgbmOH1h5WdoFR+05Xv+qADIF6ccgpWAErAvBhmA"
    "GwAtAHBUVBN8KQFUP7YdFCESTc9D09vIEpAyDw0APV/lDt3PPkC5gqSkBI8TYYgKzEGsLA2867VJHy89QLmCpqQEj4gPfT47IukSh50+EH8+UQCBbT5OzD4F0FO1KEFoBRkXiCYQBCQtBcLqyvHSfQAEEAyQIAAHCnalCC0AoyAC6tGTN6AnCBUF1ZXjpPoACLg+AhuA"
    "FwAaJOKVU5RgPgEUPzSCdTNOwD4N0lD9XS7cWREAF28RoiwJNxU2JupiiArAPhABTCmoCgOgpASP0vhxPjzD4iADIHI+BqV9nk/APgbspIEyuGCqGgcmUP0NL4YbWat6aIBsFLUgJI8SGH1KT5DgAAGAACHSUdheJmHVFQA5DCdiV401EAVAJQTFqh2ubniANKwEAAVK"
    "OwvEzDqioAchhOxK8aaoFQtUO1zc8d1KHHxKAoAlAHBTFjElSRW5ME/AQAfSUkCZXDBVDQAXF5ArA5qkBI+S5HFAPuFAMHNANIaNZn5uISVMEAiAACHQU2OqcFXRFRdQKuR+BcT8yjp6DECUNOQHAAZsdU4KuiKgAvzgrK/ahigVCfmUdPQYgSikfgaFLgAggBiAHYAi"
    "DNMJHAAXABmAGABVAHBvloH+MHl2bshkDNJQxdjuPNUNABeYh3eaJxKYLAN+pASPL+GICtCMF0QtqAoDgKQEj1OPcUFAKdMSIANAc0HflzQj0RJRzBEABu6gG3qvr2o6BJOSBzHfBvwj2+TY8EyBryUC/mwUIh4SxOAkMRZRxGEAGO9SbXtk/to6BzU84MKoVoyA3GZZ"
    "xc8KUoG4O3AQdq4VoGwUZSAkj1ysMm0cUhACuCEADezU84MKoVoyBraJeS2SeoiA4O3AQdq4VoC3u3AQbBQi+hdvdX0xQ+nxUH4x4rt1s1MmWxmAACEmORkGJcj9DoE4RFj8KayMgGwUJSAkj2K3iAzEswXfTFuL47PaWjHIAAM1ICSPcnoU2T1TJhgZUMAM0tKmYIrx"
    "KQAtxzhZ1T1H8MAFzYGS6srx0DQjgBQACLRaWlTMEV4lIAW45ws6p6joFRsDJdWV46BorYiCIpijIhCjAiUAcFEUInQQApLUP+FidT5F5XBgdj6rAHkxRsRTlD4AAQdrUERPywKIgPndWox4yIiAbBBaMVCtiAzMmYgMBkIH5p0vAwz4jMgMIqcaTQ10YctGwEsG01Pt"
    "c1DV/RUAFjwq4MsQBfxHDmp9rmoav6KgD53VqMeMiIgVEBb9R0EjSBgCktQ/sI59Pkfp8HB+PpfsdSVIwDIjOB8XGkQnQ/xj9CUTkiBWIhRUShKQID1VAkAWVkrDNnnfSMjNYB4QBSBEAwikBI+ChogKwMqJCiEkyCETFEoDCqQEj4UjfTpmzTowJpMeHFi1ZWBsnHkk"
    "9CMT3CwAEtNn7pxt7eVRADiDcF1v9TtAqRYEdGTdv/vPyrPy2S8XGHv6lBACZE4E0iTF6a/gtDIYEwAYiwI6Mm7f/eflWflsl4uMPfxs/dONvbyqIAcQbgut/qdoFR2kSYvTX8FoqKwpWhMegCJYEw8cABmAVQBwRZSAklSAkxQ/nSoU8S1slGnELgAH0XNJBSQFDU0A"
    "G6Q9V/NlO0C5gi6kBI/X+4gMnFfIDAzS8CzRwUXhVQCbtGb/D0xYDAMwpASPz8pxT2jCyTADJZcf7HixYU9tMvAEABCvIX53Lp1RAGKSgVJ2K0BAqSKk6Wo9v7vPyx4HOn7UmQv6KcQjBcqLb5OSI2AUMvAEABiRUnS1Ht/d5+WPA50/akyF/HXkL87l06ogDFJQKk7F"
    "aAgVFRbfJyRGwCihT4QmTBhQTgYZABkARQBwRNSCTiVVdUFtMeAEDNDsB358Yk1NAA4gqLLIJRLUMgMopASPdq6IDDLgBAvyFX5TyoFVAE3HnmoNFVgMAAoqpASPPdgKABMKgIBXapAQEgj/Bl4mABMBAEglIjwvBVDCoATQBvAGIimjwCLI9SKsnwoGMAZQDKAKiIdn"
    "3isAEuIwLSQS4zCC5AgmJC0SnDAAA7qdFQM07gh0UCxIQAhAlupASR9l+xRZMC0QGsAtFVgwD3U+1zUNX9FQHzurUY8ZERAgqhOcJWiDEDNYMCccEhNYMAFzIEtlE7wtAAI1IFFfHGAqACEKgIEu6kBQEBQ1BCdE0yaVT0wSTDUIAQwDaAMARAl5DmluS1ajjUsFEowB"
    "AgAGUAcgL74EUfkTzg5W41gKCkoiHzPhMQApCoCAY6pVGkG0GgMwAQQBZAEmAVMEIwhQAAdMACgGggREAx9I9x4AZQzARCiPADgHAADDJNRHAAYoIEY8ygoh6jMKIsofH6otAFUMwICR6o6MCAtCUQAZQBmAHAAbwBpAGyJAwwPAJoAoIEqUDAAEGBRPAFEMwICSEFUg"
    "JaRwAAAABBlICRR4EwICqZCJYBK0DwtEeBEQEPgRABDwEOwQ1BKIMQIQ1BCAAReYIAMRLBBoBoIXBxA53z19FFAQDQURIF8UIPwREAfoJbcQqvNOEhQPBURRJREgAFAEEuwGE4kQBBVREAIjU99nJP0vw81CWEAijEAiVE0QBcAOABJCL4IAGQ1AdxKVHeAA4AQQBuAG"
    "4AbwB0AGEAdABpAHYAZQBEBsAgQQACAEYBAEEth/AhRJREgAIlJZyAEj2LEFARyIAAACqJglNunJPzd6zxCWrywC4AcijKwHYAmYBoIGoblYY1Q2DICSkYURIACABJAFMATwBCI8WwJQBVAFIIA4JObffE8UnIoCAAPg/QgmfH8OdAB5AHAAZQBDGkAcwBvAGMAiIFEi"
    "OESZOyUTfhKQBhSXFZLSBRAYlBUCGqFgAzcjzOsKsP0EVABPAFAATwBC0Cfw2wETgBJAEAWXFQ48W2YxkxIgAnUBohRIVQcAAJEBBRQELQA0FAwXNH0BIWQvCrefNwAfDkBFqqQQBCkiHLUGuAHQAaQBuAHUI+yyAcwBClMjXKAin7IgAGwl6IMGVAGggqh/lfscbA4B"
    "KqQQBCxz1wJ8AFIIwt1xCGqRCDAiJLAi5LKACAAiFJWzAEsQQGUQNSAaZGAwCqFigQb5sfURAHLu10T8qVRAAR/U7T8cVUC43U9qSm85QKqYACNgEgdJQKEAgNQZmZnhaAMwEgB4HyT0zAF4H46AJTHr4KwBJfD9LdcAA4D8ZAQMA4D9qampA0FQcqAEEAYwkK0SdA0I"
    "QoICjPmCgocxGBQSjA0CRKqAEEQlueIEE/MNQ3cgUAYCd2qAEKQVbA6QwAIFAATwCmMJIA4oYAkBqoAQ5C2QANXJDmML7d4wYAsB6oARJIgaEvwOEAnsFAQEoAQQBHACEwcSyTsyUA0CeCqAETQ70gAFQCMmZOADaA0FjCGuAGYRQEkV5gwrHHBEAAEAsD8UrgehetR2"
    "D8CtejcD0KxzJjnw6SU68MqgE6wNCCsc/ArXo3A9Crc/F4ECQGsMq3P4EAqDAiIIgRKDAtQgNTUs8AAIhCmAOgAwgDcAMgAwgDkAMgBVSQBQQpQURFQi9O8JFBQ/i+b6AGARQHhSIAuwERAQnQKAbiqscyQfzwLA/BaQEQUCtejcD0KxzxecAiSC8AMqpAxsPxADrBF5"
    "DK0QCawRA4IBIIgiBBKvEVCA1DHE9xKsEQEYIAh6E1AOAAaECGAIhAhwCGQIegiWCHIJVaQBQQpQURETLA4CUFBpa+MTTgKAkxAiiBEkffYAEClOAs9DcUYAKDX02WnMABADMAYKABggEAAAAYIBIEgSBBEAACkjvoThbNauUpBJ8fG76euzpts8hww+mSReDRwGt9AI"
    "BwDsDGRBlkVkQUtFZEHreGRB6wxkQRe6U0GsviAqB4HSBJdXIRVAwABSAAFlVAEANwAAAFlAR4/v8g4+CHAIdAhqCIQIYAhsCIGVgB4AHwBVdAFBCkIEwlBSAk1QUgIwUFBQUFAKqdcAkAERQICT0MUgJYRocBKAAABQEwbkBDFHfRoQBKBQAw0AA+D9BlHgRogBRgAA"
    "kBpAbgQARHsBA5D8cQIOjAUABD0P6pBgtRFT7Iek/QGAAAAMEADkBpB8CAgRAh1hkKhUCikP2XAEDDkP4gcQAAABggEAAAAYIHgCASBIEgQ7hAMAAhA+CIAIcAhkCJ4Ibgh0CHAJVSQBUDcDxFBSAkxQkDcJUzPsAKYBEUCAlBDFLXADAAmNSAltGeAFGAgBGeQEEGBg"
    "AAAABAAAA/wAAwx8JWQBBQEMUd9GhAEoYAMACQD4P0GUeBGiAFGAACQGmqqkGC1EVPsh6T9AY2gNDPQFAaaHWGQqFQKKQ/ZDM1AADT0z+IGEAAAAYIBAAAAGCARZAgBcNgcgdIElyAxIRVAweRZZiE4AAEIWUA/v8/v8iA+CIAIcAhkCJ4Ibgh0CHAIVgBkCJYIegh8C"
    "IIIdAhgCVQkA0EKQgTFUFICTFICMFICMFBQUFBQ/bxonACMTwIBpZAZGiwBAwBBAEMARAAsAQQAMgAwADIAMgAsAQAAQEghiCGdifgwAIwqAXOQGkBACCGIIZ7BxPQBXCoCAauQGQJAQBCkkAbQBwAGUAcgBpAGEAbAAyADQAQhNAGUAdAByAGkAYwA1ADAANAGghiCG"
    "EQDWEQEvf84RJADkAUmAgMnkBkIEEMQQxCAsNCAsRCAshCAslCAtZCAtdCAttCAtz3rJCwAbCoBDZAaQEAQCCGe3fuYAfRSASKQFLAuAAAAGBmZhlAAAAAMDMDDNAAAAAABoZhlAAAAAADMDDNAAAAAMDM/GpAAAAAGBmdnFAqQGqkbgJkrN2tBECLfpN1tcwtg/qQIL"
    "AGQGoABwWPUBAlBlAIMAAAACJAqamqqqkLbgBvAG4AZQBfAGQAZQB2AGkAYwBlAEcQQBOAFMASQBfAEEAXwAoADgALgA1ADAAXwB4AF8AMQAxAC4AMAAwAF8ASQBuAGMAaABlAHMAKQCQVNAG8AZABlAGwA4gLghCCNGQDKKCAgj6DKKCh+UWV0AXRSAVmQGLACqqqkF"
    "qlRBqQILAFAUBqAAAPwpZAMusQJEgCsAFgpBRsEOARBBEIEMQCqAKCNII0oICCsICgofchZdAF0UgFekBiwAqqq2GCQGdfMALQAAIAKFAYC0GAAQqAoKH665YAA9QkBl5AQAQBQIBAWqapqkBAFAgEBapqmqQHOzDgP0hQYFkAYAHlAgEBapqmqQFQIBAWqapqkAqk/k"
    "HQgB5AEIAbABvAGMAawCqqGAOCSoLkZAMR9ozXEZpCAmkAEGMAGEAeQBlAHIcBkABoguRkAw3zHDtQA7QkBmEUURJG//9GAwBCIvEAAEcCJEEAZgAAkBABAFAgEjcBICJhMlT+pQpwYJhMlT+qapAQCdMxBjVAOA/TanAFAgECNkEwJhMlT+qCIUEAeYTJU/qmqQFAgE"
    "I1AQaAMiABRuGJqkpEwAGiqT+QZHAGwAbwBiAGEAbACqp2AOCTILkZAIh1cKmABuQwCAuiQGQJAkBkCpJKwVCAR6TUzMzMzM5J/DIggSATM9M/BYAwjMz0z9BkGqAAAAMHhnAQAPg/BrLQAUQCKTFgAFdnAGAA4DAP5CUJIuQgiECHAIdgiYCEAARgg+CEAAOAhwCHoI"
    "giK8FQAgCHoIbAh+CIAIfAhqCHQIhAk+ANB10HXURZSAjBSAuJQ/Ww55AE5DAHYkBkCQJAZAqQFYGAASEAP7///+BWvRuB6FW5/ArXo3A9Ctc/ArXo3A9Csc/QFAUBoAbCdkBgisc/AK16NwPQrHP2AP/CcAFBCmAOgAwgDcAMgAwgDkAMgBRgBgEHXURRQURFQ/cdh6"
    "AFZDAHlkICv0AW2FAHRHMfcBcEOQmB8GYdhTAD0SQEYkX9sDAAAkoBgI+T8GC1EVPsh+T8AkjB0DDgP4AAAAJAQfAEMAADgv4AAAAwABCFMAVABBAE4ARABBAFIARACjADAIIuoiqiK/HXoJAB8UAEPkBkAgh38LAhMAHkLAbeQGloGYgB0AGIAdAGAQbb+lmB0AJkLA"
    "gEkkJtIdAQBgCAoZAB0AcFuQbb+z3B0AZQhklQhBdQgaZAgC0G2/wd2FCKSVCFGECAADgB0AcFwQbb88BggCfkTAgGqkBpSnInQbBwABcD0L1qNxnH9csQcABcD0L1qNxnH5dAUGvH6MwAAABgACIqUiGC50AC3OAPoCcKYFdB+gMAAAAYBU3wBnGQAMIGBWvRuB6FY5"
    "+gMg0DBaiKn2Q/J+MrmWnClg6B+H+gcY1N4+h+MrmWnClg6F+eUSn8Sepfp+hSSANoA4ADKAOQA0gDCANgAZABoAIUkgDaAOAAygDkANIAwgDYAGQAaACIJIAWABAAJ4AWABAAKIAWABAAKYAV4CwAFUAQzQAvhKAHgAuACCAMYArABYnQAaQACsANIAygDuAKgA8gDg"
    "AMoAQAC4AMwAQABEAEoA6ADGAGIARAB8AEoAQAA47AALpgDKAMYA6ADSAN4A3ABwtgXkAOgAkgDIAF4OWgAgB+0AimDEnA0LuACgAKYAhgCCAJgAigA8BAICxgDCANgt/AIB5gDcAHQvABqDIIAnACmAJIAZgBiASQVwQJCAahREVBQURZRFlER/TN2/AX5EwICXZAaU"
    "s2CDc3AAKIFgg4UDoo4BSIDgg4QFlActzAAifBQDAAAAFyAg3IIkqhIAIoYHAiAgCkQIAAeEJoAygDoAOQA0gDGAGoAYACEJoAygDoAOXIIEYAagBgAIgj4lCLIgB0QGICk3B0AAUDscCDwGB1IA7HACEQRwbVDscA4VJUUDgQJCAGHkBABCFlQVASKcGgbIAEBoAAIA"
    "AKUkbRkAJ6gWABguB6F61G4rj8uB6F61G4rj8uB6F61G4rj8uB6F61G4rj8CtejcD0Kxz8AlLBcI+QRAkDQFBUBgAgBQFAwAMgAQGgAAgAApQWAAAAOIcQIA0D9ASzZEAZgcJN0YrCjcGAEGQGQGI1wbAg/v///4JMwYAac/QKQxUgBBJDFRAEIyUQBEMlEASDJQAAZA"
    "UBQJBUBqAAAvTAN5Iscgk08DkBQNLU4DQKBsaSCaTAMASdAkIUwB0AGEAbgBkAGEAcgBkAJBVQAYQBiAGwAZQCQZfAFQASQBUAEwARQCQdfAEgARQBBAEQARQBSAJBV8ARABBAFQAQQAqAsAgwxkAghgoKIioKCgoKCgoiJVAaCcAQAFocl85QAlQoBn5AZBECSAoEgK"
    "AoDICGZQAAFnxn6AJPAfAAQHyAgMf///4QAgKAoCgiAwDgABhgCAIowcD0ACAoCgKAoCoDIDAAAAGQAIClgDAAIMgKBIDAOAAGGAICgqAyAyAkBQFFC+D4DQEgJASAkBICQEgKZIDICoDGARAAgQAgKZICgaAx/gABhACAkBTJAUyQFMkBICmSUYFQA3MgSAoCQFQFQF"
    "CzIAZABXAGkAcgBlAGYAcgBhAG0AZQBD3MAdAByAG8AawBlAHMAXwBvAGcAcwAuAHQAaQBmALQB4IMgzP67v5VQ6BICXJAZBUCRYKCA4pAMBBIDQGiAepQMzIBWkAwVoMygzPz5L2VQ6BmekBkHQKgKAyDxNBzI1SAcFKEIDAOAAGGA7TAcgIaQDBAVCAGEAcwAijD49"
    "HAcHFQB4IKgzP2ec6VQ3BGlkBkMQKgQgGcgKIAF8AyWkFwFJQEBkICGcAw0IQgByAGkAZwBoAHQAZQBuPtQKAAUhAHghiDM/u4ofACVBwIFZJAYAQgxACyJqRAAMhAAJIoAwCECsf5fWEgAtXAgOZAYAQExABoA4IEhArH8NSRZ4BQACpAYAQMxADoAMQA6AOCBoQKx/"
    "3k+FDORVDABUDAAUiECsf4HKKgAjAQBX4VoAAIdQ0qAFAAYQBwAGUAcgBfAFMAcABhAirEEPAwANoA4IEoiHAE0NACUBQFghWAsMWCBqIh8GPRoAGwEAgIxhWAQBUFXwBCUAQAYFoAwCiIdFAg5TDICMoVgHBVggSiIfI0keZQyNUBEDgxB18ATwVBwEBuADMAMAB2QN"
    "DHZQLwAmBMCAjWFSgACHoCMKJh4XIjwyWAIGAkxQEuChNon+UAMIAAAAAbBAlEQ/yq2NDKG/DAAAGG4IB4WcDg4GkxQEuChNo3+wQNREP4btJ30Z4TrMAAAuAbBBFEQ/mCj8ApkERYCAqeQGSdJ0VkgQFAkCkEQFIECP////8/////0CQJAkgQOj/////P////9A0gQR"
    "AUBP/4QHAAMESBBkDQM/////z/////QVIEHQRBBcCVgECtBkgQlCEIQVCUHSBCigBQWEIQhIELQdB1QIYA0DJSBDEFQUrAcDpIENQZBjnBsDQtIEPQlCrBsLDEgR9DEPQpEUNSBID/+AIQYMQxDkgSFCkKOQDQND0gSJC0JQF2gwARBIEjOoBgXQ9EUgSRDUNJwbBNEk"
    "gSVDkOOcBwNE0gSZEESoFgMUSBJ0RRGoKgFKkBkCkANpFgFUAwHQGQGQoBhkAgL9ApAkBlgGnSD8mBsC0DkCkEOSG0BQWAIC/QSQKQWSC/QMpAoCWQFBkJOYCl0H0FRFA/0GkBQZClgDXhb0FWxRA9B5AUGQg5wKeA0C/QiQFB01EAICmQRBkLOoC1ASZDMCCpAUMQ6Y"
    "FmUEC1QDAtC5AUMQWANkMQlCkNP////9DJAkNQxkB6QGZAMC2QFDEROaFkLQUFYD/Q6QFDESVAdXGvQ1EFgCBND5AkQQxDCUO1QGUBID/RCQJDETUAhWBPQ5bF4C0RkCQxFYSmAgtGcAzACEBUxkBVBkBVJkBVRkBVZkBVhkBVpkBVxkBV5kBWBkBWJkBWRkBWZkBWhk"
    "BWpkBWxkBW5kBXBkBXJkBXRkBXZkBXklS34A7QFGgICrKj/////SFxTx2EGSFxY9MIJbDykCUAXp1b+vNaAECQlAUfQFAWAEMHwQ1BEAENQQ8BDUEQQRCBDgEQgRMBDEAQZYAEQAZQBsAHQAYQBBlkARABlAGwAdABhAJ4B4IKhAWUhAWKhAWAhAVShAVehAWahAWYhA"
    "VqhAVp+GLIUARUbAgKtqP////9IXFPHYQdIXFi8IAgAmAZAUBQLoA4XWIbMHQMC1PZ5VkNk/4Ndrwxfp/j/UXg9GwJcFQEBQGmAEJIAQwBEEEQgRPBD0EQxQKAERBlgANXgCABAbgHggyEBZaEBZf7Lk3wARRwCAq5GVIC5woz5CYo12fGPzfQFrJfJKAAoicBAAAIr0"
    "hcU8dhCUhcWqiV3aGQV7CpPBYdC6XFUoHQKqQqqADIqw8gMPQ/OBpL6K5mfo/kKQgeBEIEQAQwBDcEOARCBEwERUeBEIEQAQwBDYENQQ9BD0EPgQ1BCAAQQQ+BEEEQgQ+BE8EPQQ4BDUEMQCQ0RBDUENwQgAD4EQgRABDAENgQ1BD0EOARPBEKHgRCBEAEMAQ2BDUEPQ"
    "Q9BD4ENQRC1UAcABkAGEAdABlAGQARgBsAGkAcAAkBOCDxHjSwAQR0CAq+o/////0hcU8dhCkhcWQxDQAeEvBkGHBPyQcJ7a7CbiP4f////6Fkru0Mgr2FSeCw6F0uKpQOgSCkAIhgiOCHQIYAi0AcEIPgQsABdGQICsKj/////SFxVGkLQlC1UAcABkAGEAdABlAGQA"
    "RgBsAGkAcAC6AOCE/w7TNgAXRkCArGo/////0hcVKAAAAAAAABEAEMQlDFUAcABkAGEAdABlAGQAQgBhAHMAZQBYAMoA4IV/cqY2ABdGQICsqj/////SFxUoAAAAAAAAEQAQ1CUMVQBwAGQAYQAiYh5kACRAIgABZQBZAMoA4IX/tkuzAJ8CR4CArLw9CkPSFxYM+QmK"
    "Ndnxj8OAeQAu+QtAkfQFCUJQlCUJHgRCBEAEMAQ3BDgEQgRMBDEAQRGAGwAaQBwAELVQBwAGQAYQB0AGUAZABGAGwAaQBwAELfBeBwgBhAHMAZQBClXsQwAkRQBuAGQAAgPghiEBV6EBVKEBVCEBZaEBZSEBYqEBYCEBZqEBZiEBWqEBWn/1JAQBE0fAgK0RbKQM4IFS"
    "bYKCVAKXq75ahnA0IyocAADMpABAEfSFxUggAyHiHISsFQAAuv6mv6sBQIZnWkxczVIkAALr+pr+rAUCQFI0BSNAUgQFIEjSCoQFz4A7ZA2D9AapCBsEOAQ9BDUEOQQ9BEsEOQRDUVA8AcAcABsi4DIABsAZQBtAGUAbgB0AFgAQ1EAGkAcwBwAGwCRMIQAkBtAGUAbg"
    "B0AFkAQ1EAGkAcwBwAGwAYQBjAGUAbQBlAG4AdABYAENRABpAHMAcABsAGEAYwBlI/QvB24AdABZAELIAQwigGEAC0EQgQ+BE8EPQQ4BDUEMQCrgTghvdoZUABJIAICtKJgQC0gSFxZIUiGZ1pMXM1SBoDsAKKf////5mQ0ZjhAsNoFIcNAh8CHoIagiOCHoIYAieCEA"
    "AgAiGCI4IdAhgCdQBwQ7i6Y0ABdGQICtqj8jCxQVKCYi5DQEZm5f0hR9CzLlBlhUsgKH/3PVNHAOiJTBDiQ04QBZUA4CiH9ZnlJqMq4qIqQXI9AVBEjSFxZJElAu3AbIMgo3gUhoiCGAIbgh8CGQLiADBSbQBwRHXoE2bSOuhUgVJRhxAxEAEkR9DPAymcdYWMcBiX/d"
    "FIgOrEB0lgERABJUNugAZNYIif8Z+ZYAXUbAgK6EQQAqFPHYSZIXFjbzZl0VSglQC1Y6irs2kDQJApH0fQLstdUmrZ0lQMAf5xQgheQ/AJirCmIhBkAAC/qDlX0OJPoWKIAu+BYBEMgBCXDNKhgXCEJRQBuAGQAWQBEAJqwZAAY3gHgiiEBZSEBWqEBZX3KsegCPAUaA"
    "gK+wWglJ0hcWHc1I6cm8CVCU0QAGCQWR9H2AELHwQ1BEAENQQ8BDUEQQRCBDJKIWJRQj/D4EYAEQAZQBsCM8P4EjWSlMGQLuAeCKoVnvZmzuACRgIQFa//iLNADVAUVAgK9kBkGAgLKAgLLAgLMAgLNAgLAAgLFYIuhAVMhAVKhAWAhAWKhAWUgjGBoANIhAWb8aGBAA"
    "RUhAgK+kBkBYIwhAVMpAVL/4UyQAIQqAgLBqQFAQFCkEAQwBBAEQAXwBGAEkARQBMAEQAqgDAEQFhQzuJABTCrGqQDugAAGPjSkqVhSBLWEKNbQUAIMQASQBNAEEAUwBTAE8AQwDaAMARAlvkzdGAFFKAIEvJAZAQAGoCgSA1RNMj9ihw2wpREUEAYwBEAGIATwBzAG4"
    "AYQBwAFAAbwBpAG4AdABSAGUAZgAaAcAhAl2hAl0hAlz8YQNACMKgIBj5AaQEAQCEAx3qs0JABMKgHmqkBASCIdKcEwBekUAgGskBpSBwAAABgABcCS2X34FIztna5+BIuxCJxBgJbhfIrQ3CWAAFwPQvWo3GcfoCGixAgHQfoCjIzFXACQcWAMAAhSSANoj+1zkANIj"
    "IFoCZABoAIUy5F4ALErRKAHgAuACCAMYArADCAOQAQACsANIAygDuAKgA8gDgAMoAQAC4AMwAQABEAEoA6ADGAGIARAB8AEoAQABOO4AIANcCgAICANIA2ACSAMgAfABKALgAoACmAIYAggCYAI89AAFmAMYAwgDYAP8HgGYA3ABZB4ACwAAPgEIBq1ERUFEWURFRFlE"
    "W3wS9gCCAUUAgJeklFRsRgEAACiBIkhoIphSYQQoJaxcdFJrBAACiCTDcQBcgC4gBQQQmgDKAOgAWFEDxgBqAGAAL7JbSbkgDBAEAgEAAUABOMQAPeADBAFIBIAnBs38PgAHBnAKABMKgIBlKpAQEgkXGoMhACkKgIBiKljHAyEYAQgBYIy6ChQBUAIoAoMuRAMTV191"
    "CWFsxjKUAAAKLEQDD1Q+igCJAQqAgEQqQVAQFCEIAVQBNAFAASJgTwBGMAEUAQtEAEkARgBGAFUAUwBFAFQASQBMAEUAQhGAEIAWABBAFMAUwBFAFQAQtPAFAAQQBDAEkAVABZAFQASQBMAEUAQ5SAEUARgBMAEUAQwBUAEkATwBOKAXAAPID4LwRAIkRAIiRAMURAIm"
    "RAIp9FR4Og5BKpAQFgvvP6KyAAtFwICqESL0IAeqLkGzTtewZAXpJFQvcHcq9CACEBSFxaAuEBoAEpAUCQFAkCLCSa6sQOvs/NQlgKJ/fQNAkFIgQ+BEcEOgQwBENSAVuB8Ih8EPgQ7BD4ENgQ0jPCsisB8KK6AsBwynOQAQRgCAqiUkGwcU8dhAkhcWQNBALmwCIoAc"
    "AfoKQAgpSCoBAokvJiMdHKonMBsBkDQFCCz8GwZYAIoA4IH/AHyICiXwGgEVKJBELqkAWVgKBIJ/bQUcADki9hWkBliNAAIRUAEUAWABUAEoAwCEBYJEBYcLW3IIseQxgAAPjEQFke5TewBuSgCBLeQGQMABK/gUDUAUBQJAZommR+xQ4bYUoiIiwG8DiADEAJ4AIkhs"
    "AGPCAOAAoADeANIA3ADoAKQAygDMAIiggDGAIgAxACeAOYA3ADCAOAAoADeANIA3ADoAKQAygDMAGgFgEIEtkIEtUIEtEIEtP8BN6BYjE8CAYmQGNgWAABGAAEAWgDmH50ZAQAkADUAMAA4AEIAMwA1AEMAOQAsiKFoAAUARQA3AC0ANAA1ADYARgAtAEIBUBAADDQAL"
    "QBEADUAMgA2ADUAMQAzADAAMI+iPCA2ADYBf1BLAwQKAItBlCi2cGI7Pe4zbnkAAAB4imG4APcAAABhdXRvZGVzay1kZXNpZ24tcGFja2FnZS54bWw8P3htbCB2ZXJzaW9uPSIxLjAiIGVuY29kaW5nPSJ1dGYtOCIgPz48Zm9ybWF0cz49wAgABD5odHRwOi8vc2NoZ"
    "W1hLjYBf2JwYAZjb20tQG8wZC8yMDA5PC9mb3JtYXQ+PgAIJHM+UEsDBBQABggIAUC0B9SG/ZyL1JD0iUIYPwAAAFtDb250ZW50X1R5cGVzXUCsAmB9jsEOgjAMhl9l6R2KHowxDA7qG/ACcxZYhG42AX/ZisG3d4Sr8dj+X7+/dbvOk3pTTM6zhkNZgSK2/ul40LBIX"
    "5xBtU3dfQIllVlOGkaRcEFMdqTZpNIH4pz0Ps5G8hgHDMa+zEB4rKoTWs9CLIVsDmjqG/VmmUTd17zeex+OQV13rsuYBhPC5KyR/BZ6KyRFkkhmBvwpyP1/BFuaNgF/73BTp+YLUEsDBuDUIyjtKGvrAAAAfAEBYZwIAGNvcmVwyAOMjZBBbsMgEEWvgmZbYYMhjW1ho"
    "lR2T9ALIExclBgsA1WPX5w4UrvrakZ//psZfXH6nm/oy6zBetcBLQgg47QfrZs6SPGCa0AnKVbv4y8bIKdm08E2AX8mgxTT6tOyS9q7aFzMqvOj2UUVgomA9C03HQT9aWZVqBSzI1yLRemrmkxBn12GU7IjehyxY95nL9asIJvzwI4NGzDrGcP8nXL8xusjHvoz7elr3"
    "TQVF+UGSxHt/LyvV6OiGUFWhDSYUkyqD8pbcmj54YXULSGi3Ox/oLSM/4SSNgF/dZFV+7sPLICk+ZH7QIpyyyKXe1C5brnJH1BLAwbhFAtVAZ6iXa0UAAAFYqABX254LnhtbE3LOw6AIBBF0a2Q6RXtLPisRQUMEWYMgmH5irGwesnJfULXGNhl0+kJJYz9AMziSsbjJ"
    "qFk103AtBKJKP8yYDhHNgF/K6ExKLElKsdHxrq5hPxo8Lh/6JYKXAn+hs+2n7oBU4J0J3vEGshxAQAA1AMAAIyRmAZieC9iEaAAAcDFU+1ugyAUfRXC30UBtWttkKZLuyfYC1ClzlTBIJg+/q4fTdela7pf84eSc+7lnnMQvjk3NeqVNgF/7SqjM8xCipHSuSkqXWbYu"
    "2OwwmgjuDXGfSvDSMtGZXiAseClNb6dodxop7QDVJtCzaDsOuUwymtYZLjLP1UjQ+kdVHSnsJX5SZYqZCHQUCd45ywIQNOQ4Y3F8XDmZMIF974qZrYqYFp1rJTFIt3u42Ua74N4F8dB8s6S4C1ZLTYBf4P9bst27HWVplHCydAsuKuai7rcKulUgUVEaRowFtDogyVru"
    "lgnixe6WlPKyVB+0+Tb4skmX2kXR7Pcqa3DgoGQkfjhFiJyqJM96CGCkyFE+IwJ3wYNgUDITh7qi48TQL3KnbEJMIXxV6qXtVcwlYZ0fNDvC06mTpg6bg6u7842AX+Inp7xeEc4aqlLMCEdLA/eDTr5pGEOrVU26N0ZaWMbWT9n44HDP1FX8Xcl5aY29r8UkfmAyPx7k"
    "OE+ii9QSwMEFAAElYBAO3AQKkh9AAAAnQAAAAsAAABlsaHiLAG9zNEKgyAYhuFbkf/claXDAzWszfuIZSEzDTYBf6djl78aHezog4ePV3Sf1aO3TS8XgwRyqQHZ8IiTC4uEkmfMAXVKpBjz3w1QGFcr4WBQYkmxbCdNdh6Lz7t6F54n9lyzmg8U05YYTJkhuB80w6yht"
    "Lmau25vBiolql9p3yOsvlBIqBBMPzYQyjMpAQAAEgIAADEANgF/AbCoAFNCOEE1MDhDNC00MzFGLTQ1RjEtQkNBNS01MjQ0MjZGRUEzREYvYgJ0AACMjVFbbsMgELwK4itVhQ0ORG6EiZK0PkEv4ABJUWKweFQ5fqF2pPYvPyyanZkdWL67jzfwrX0wznaQVBgCbaVTx"
    "l46mOIZtRDsBPfOxTYBfz80COww6g4WGAp+8S5NCySdjdrGjFqn9AIOIegIgbzlSweD/NLjUA0pZka4VtMgr8NFV6TK7cwTPESfA4B5SDmhOLR7htsjRXRNekRZT9DhuGeINZQ2m/5jv37veT0LBU/JqEVuVI5jzkb7Z02KWPBoxkd86fUQtYKiwfgNEYI2AX9w80noF"
    "rMtZa+43WLM60L/J0qTelKUjI3rZok7ywIUhNdzQ3Dl0un2CKPvk/MRlHmroOULFLjCmBGaQ8zE/PzsuKGLY4jO5+9dXU+ZS9hsu6GC12VDufyuL9eyTfEDUEsDBBScIGQrG4YXkU4BAAAzAwAAMIlx1A5ieDYBfyyAGAQaeIgMSNWTwI1gWAABCH8Fca1s49SJ0ggTq"
    "Yd+QQ+9YtgkNBgswFXz910SkuaSQ4+9IGt2mFk9Yb79Hi35ghCNdz1ta0YJOOW1cfuezmlXrSnZCh68T3c2NgF/SpwcoadZpoLvg5+nImnYydkmVK1xxyIGiH4OCiLK+SaxXkmLAeCqGUUYB9AaNLkZ8WsHAVdBcTiRdADy9vpB/PAJKkXe5BTBm9wheD5L052JEmVlj"
    "D2N6gCjrOWcvIZ4rLVMsm7ra9eDnX6TSL5wrZyDIbm8p/mkomxUI0fe4DYBf1DwmALSK6Z0moAKOU3WKJkQcnM2XjyCz8alVVe8BsEHdLer567DsPNM8GRGKA4VQCbQVCwYe6natmKL97bbsOWmWz6x9YYx3mS74IP3tlzCGAh+Isq7BC5R0fImjx/hKz6iTUDWPpz+A"
    "BIBlNYLnVvGf+bTnN834gr4F4gfUEs2AX8DBKPAXCu/7y47aQUAADwQAAA19aQsgBJAGAAAAAAAAAGHb2JqZWN0cy54bWytV11zmzgU/SsM+wyY2E6THUIntpOOp5O2U087+5AZjwCZsAGJkUTq7K/fIxAYsDYBf9N6P/xgkJDu57lHV8H7fZFbL1TIjLMb23cntkVZz"
    "JOMpTd2pXbOlW29DwPBueotsy1GCnpj62k7DFLBq9JMJXRHqlyNZu8Xf1gypozaVpwTKW9sGT/RgrikUjyh8tlNiCJuutu7vtssHIpNBSmfRkJLIihTsBTzDFKsxih/OJw2AX/YXhh4+nsY6H+zavr2Kq/2Z6g/Y1IRFh8pG4mZ+rPV3cX82pnPZlNndnnhO4v7xcrx3"
    "00ny8vl8vr27hqKpRKQZCwRdGeHHxAbkcWB13zqLDaGnzIp5ozRuPYfHtY2G4kJLSlLkMeMSmjreT0ZDn0dm97nqR4blf3p87zq7+gJNgF/am1vn31LefQnXJDnoEJIqlHVxMc42uBvcohaxHluvmXSKoiiIiO5lWeRIOLVDrFULwmDgRiNTqERrj2wQ/8gr28rSuPX2"
    "D1l5a7Kcw1NO6yRvQX+qZK1ZdlfVJzWBpuQqypj6so4pF5LaofXgVdPhoF+TC/MxyaQ1i4nKVIONzYBf5uvI0eXuvbWKzv8eB/tN7oeTysvBS+pUBo+gFabuPapo2TU+mdlTm+AM4OYH4LyFZH/hPI9mIK8iWw/28+MFiUIkzsuCuTGndQ/a9K+ON3b8Qv4bLT6eE038"
    "68WB15n7JAw3sofwKVTc/Xf8zeMWR+pvfSFwQsKjIupCeUmJjk2AX+o5yFjSIgGpZVzTIHLd9HeDtdgSjA7dpE87AJy9BJ4L/iO/0Y22KpW33syJHTEt2cwP2JZlwVsewMsRzxZKzbOvRXz+f9SM7erzcdNJXYkpg+GWFZ0l7FM4ew8gLdv0CARA4+e6esPLhI4epyET"
    "T8JhVElEW0dcx34tD0s9OCgNgF/eaAgxr6Ua84LfqHhIZMxzXPCKK9aLd0xpLHakYzpE1CFTUCnFyMUC/qS6U5isGJgFs76WGSlDll36HU87b7hy7f1J4DSDhevC6D1+bAqOtB9zHMuttHrtmFCG+DDniG6vw/hbSLqaSlAfI3llnJMiLdJtttVErx7Iorf18t+pjYBf"
    "zoiOX5pC6jV2NTkDOyM2iPCwLfViYZAEBzsnG0zHOMoy5PK+7rHCmQt9w35UVWUW1LwiqlzwjRp/Wmt74T3uxj5g6j4yQ439dNZgLITmhxSNUCBPoJO+DRIz3xytZjOl9fO7d3dO2c2v7x3FnfvZs5qfnE596eT6e3ysrOotiQ2AX8M2hOqX4OIJk7EoBKZCfO39aFs7"
    "fCBKOl9aArKS5vnt7WLtjjwsAcA7zauizKnBWWKaPg+6Jf8K0FXMZDRzK8LktIzpHz+sBnZgJkz9n3RpUZ/jPaa2aWuhZNC1FNVRIxk+WijcdwtWWrcbkPZPRtGb4d6ZOKJPlTyPEtAOImVNgF/Ul5QBdo5g+1FQSUQ0+/KE3N7OGP3S9MPKhLltLXkiaAlziVQDbhVs"
    "RrOW7+hhdNd1I2Nw859xp8pRNtCqm9s8JvKYirdCMejbnxq4YAAurCOBAE1wtIcnXWzqRt3u3RsQD84AY3+bsk53ZLxa0C8BSlLnNoDWq1tMwrif+R4azYBf45FFF6jSnW+HCY6Z2o1qKzGKXM3QAvxbFTvUV8/d8t36zWDiJx1T/opCBqpjiIire8F2j5j0u3qi4dWw"
    "Fp/tsq8SpHL8yU5ggLMlS5woAioMDJLogDV5e+PXwTHXbSw7jNA4HHJi4IzM7g1d1lr84SbafIIWqD6+iEvJr7/WHc2AX/95iKyjYikLknkMybagtMejLAGQB4dpyYFns7BaPl6ZZkDYwahNWiPmtLmGm6hePTNUZdKnyzLnzb+Xr0UYBBo2cO/AVBLAwQUAAYIAAC2c"
    "GI7AAAAAAAAAAAAAAAANQAAAGZieC9COEE1MDhDNC00MzFGLTQ1RjEtQkNBNS01NgF/MjQ0MjZGRUEzREYvdmVydGljZXMuYmluUEsDBBQABggIALZwYjvycPEzBgAAAAQAAAA2AAAAZmJ4L0I4QTUwOEM0LTQzMUYtNDVGMS1CQ0E1LTUyNDQyNkZFQTNERi90cmlhb"
    "mdsZXMuYmluY2ZgYAAAUEsDBBQABggAALZwYjYBfzsAAAAAAAAAAAAAAAA3AAAAZmJ4L0I4QIALQJgZdHRyaWJ1dGVxUFyw4OwvCNoL0ZAAAABBAQAANgCTUKjOPG82AXy4wKAbZGlyZWN0b3J4ioDgBIWPQQiOgOAB5yKzb1Pppgs1y+666A0kTkRInGI09Pg1RkpIA"
    "10N85j/n4r2PQ5sxjA58hL4+QIMfUfGeSshxf50A9YqEYji5gyY1yNKWDAoYQOlV0UGe52GuKPPnH+QwR3mNgF/B/sUQ5bXtqgtKC6aFSrRFNXvLLhm7ugxuO6genu1qNfWGiuq63/V9wkh/0l9AFCsMNQrO0YG8/4AAACgAQAAOJXwuM6QDLpgDCtyZXNvdXJjZXMvN"
    "gF8m1DUAABkjVBLboMwEL0Kmm1lsIE0gIyjVKQn6AUsMyFWgo38qXr8mkCldtfNzOh9NE+Pn77mR/aJzmtremA5hQyNsqM2Uw8xXEkD2UlwZ234JYPMyBl7WGEQfHI2LjukrAloQkKNHXEHpfcYIFOPdPTg1Q1nmcsYksLf80U2AX+qu5wwZ3mik05wH1wKkG1P1gnCo"
    "bfRKfS82FjBY9TjrtFj+qmvGh2I9nypjm01kGqoKlK/s5q81c2RXIYzG9hr07ZlzYvVLHjQ809G5VAGHEGUlLaEMULLD1Z39NDVhxfadJTyYpX/McVl/KcpahOqco+72TwIloI8CcGLta+0NgF/nmWmvXYrvgFQSwECFAAKAAAIAAC2cGI7Pe4zbnkAAAB5AAAAGwAAA"
    "AAAAAAAAJihROXVHFGASKOAlLoxFmBAIAAAsgAAADYBf1tAv0EUuDAEuQEO/ECDAQCd4Qy7UAC68P7QNAiUAgAAYJPQ/BhQNgF/SwECFALQsLoA+vg0GACR4NZCOLsQBLtg4tg4swXnj2IQd0EkDjYBf3BiOLCQ3tA4CAAAWQUAgEVA3LmgCLpwyshg0QSI1T8AiiDsg"
    "BAgNMgsDnBiOLoAtshgbQnw+OnQBAQ2AX8wmXDopxC20MXSlJlDLURcNJay+XAICAAAKA4AgCZAEBN2ZXJ0aWNkmCBVkfwENgF/BJfQ/BfycPEzBgAAAInzIIhwVdBhWAR7DIAuUAQMcmlhbmdsnpBZqGQGCMSQDeDUj9D5XGQA1QyAKmQHYLkQYjBkkiFMuTBhsF2IB"
    "CoNws8tlzYBfOLhAK4QYsGZ4GS5AFmQYYgEDhCAB9AcnSEIC3I2ASdkmhBa22cFBInCzBwOAA4AgAQAAGURUfgACEBQCEAxHiNjkFiMTwIBh5AY1BYAtsFsDDgAOAA3AIghbAw1AEEAOQCI4WwMMABEAEQAisFsDDEANABFAIrBbAg3ADQAMVQJAVAsiZOsLDQARABBA"
    "DIAQgA0AEMAgAH2wWwPvBY49ewA+sFsK2vi2MJEcducoBdAQBzGwWwC3X74nm7oyyzBetcDLQgg45TX1o09pHjGe0AHwRfv4y8bICcn08M2AX8qg+Dj4tO8Scq7aFzMqvPabKIMwURA6pabHoK6mEkWMsXsCNdiluoqR1PQZ5fhlKxGjyNW5332bM0CglVD1Qysxi057"
    "XD9xo64/Wj2+Hh6Z4Q0LR3aHS9XWPBop+d9tRgZjQZREdJiSjGpPmndEdbV7IXsO0J4udr/QGnW/4SSNgF/dfG12t59YAEEzY/cB4KXaxa53IPKdc1N/ABQSwMEFJ2BKLvQbJbwbIB+0WwMNgF/RyuggCbRbAs1hv+2cIAK0WwZQadtbZCm3dYkitVszKbVbVim1Wy0i"
    "tFsAAY2AX+V7SqjcxyFFCOlpSkqXebYjtFsAACMw5k1xn0pw0iLRuV4gDFnpTW+nSFptFPaAapNoWZQdJ1yGMkaFjnu5IdqRCi8g4ruFLZCnkSpwigEGuo465wFAWgaMrwxPx7OjEw4Z95XxcxWBUyrjpWymKfxLl7u0iTI6H4RJC/pNsjeljYBf6tgu39NKV1m0S5bM"
    "DI0c+aq5qJOWiWcKjCPKc2CKApo/B4la5quk/SJrtaUMjKU3zT5tniwyVfaPcez3KmtwzwCISPxzS1E5FAnetBDOCNDiPAZE74NGgKBkJ041BcfJ4B6JZ2xCTCF8VeqF7VXMJWGdHzQzwtGpk6YOm4Oru82AX/OiB+e8fuOcNRCl2BCOFgevBt0sknDHFqrbNC7M9LGN"
    "qJ+zMYvDv9EXcXflSRNbex/KSLzAZH59yDDfeSfUEsDBBQABgiTwFgLQiCg/3yACtFsAHDlQssDNdDsPmJZyEo2AX/D6djlr0YHO/rg4eMV3Wdb0dull49Bwv1GALnwiJMMttFsAJA3J+FkUGJJsewXTW4ey5oPXX14XmjbgVHNKG5aU2PKa4o56Q021A6WsIb1WkOlR"
    "PUrHXuG1RSKQcShkJgLL6P+3iia1W00isFsjzB8AEtFN0Y1NEI1NC02N0MyLTQ4MjQtODBEQy1DNEVGRTA1NjVEQkDW0WwAAI0uOG6EiZTXCXoBF0iKEoPFo8rxC7UjtX/5YdHszOzA8u19vIFv7YNxtoekwhBoK50y9tLDFM+og2AruHcuNgF//qFBYIdR97DAUPCLd"
    "2laIOls1DZm1DqlF3AIQUcI5C1fehjklx6HakgxM8K1mgZ5HS66IlVuZ57gIfocAMxDygnFcX1idMcoatf7BtGuoajDhz3a0+PpiFnLDrsdr2eh4CkZtciNynHM2Wj/rEkRCx7N+IgvvR6iVlA0GL8jQjYBfxBuPgjdYLah7BV3G4x5Xej/RGlST4qSsfGtWeLOsgAF4"
    "fXcEFy59Hl7hNH3yfkIyrxV0PIFClxhzBrS8nom5udnx5YujiE6n793df3MXMJm25YKXpcN5fK7vlzLNsUPUEsDBBQABggIALZwYjsbhheRTK7RbAo2AX94LIAYABiA2tFsCgF/NkqcgW7RbAo2AX/gUIFy0WyMQMylgewPKWUhFmMEstFsgBJAGKewtK7RbAAAAAAAA"
    "cyYNMkOoWObJOPppu3U084+ZMYjg0zYAGIkkTr99XsEAgM2AX+2W++HHwwS0v089+jKf7/LM+OVcpGy4tZ07Ylp0CJicVokt2Ylt9a1abwPfM6Y7C0zjYLk9NZU02bgJ5xVpZ6K6ZZUmRzN3s//NEREC2oaUUaEuDVF9ExzYpNKspiKFzsmktjJdme7drNwKDbhpHweC"
    "S0Jp4WEpZgvIMVojHKHNgF/w4npBL6jvge++terpqdXObU/Q/1pISQpogNlIzFT1wvvLi5vrEvPm1reuwvXmt/PQ8u9mk4W7xaLm9ndDRQLySFJW8Lp1gweEBueRr7TfOos1oYfMyliRUGj2n94WNusJca0pEWMPKZUQFvP68lw6KrY9D5P1Vir7E+f51V/RzYBf09Qa"
    "3v77FvKNn/BBXEOKrigClVNfLSjDf4m+6htGMv0t1QYOZGUpyQzsnTDCX8zAyxVSwJ/IEahkyuEKw/MwN3L69uK0vg1do9Zua2yTEHTDGpkr4F/KkVtWfqD8uPaYBNyVaWFvNYOybeSmsGN79STga8e0wv9sQmksc1IgpQ2AX/DzebryNGFqr1laAYf7je7larH48pLz"
    "krKpYIPoNUmrn2qKGm17lmZUxvgzCDm+6B8QeQ/onz3piBvPN15O09rkZwUYst4jtzYk/pnTNoXq3s7fAGfjVYfrulm/tVi3+mMHRLGqfwBXCo11/89f8OY9ZHaS1/gv6LAGJ/qUK4iNgF/koF6HtMCCVGgNDKGKXD5drMzgyWYEsyOXSQLuoAcvPjOK77jv5ENtqrV9"
    "54FEjri2zOYH7GsywK2nQDLAU/WirVzp2J++b/UzCxcfVhVfEsi+qiJJaTbtEglzs49ePsGDRIx8OiFvn1nPIajh0lY9ZOQa1UC0VYxV4FP2sNCDTYBf/aaBwoi7EuY4jz/FxoeUxHRLCMFZVWrpTuGFFY7ktF9AqqwCej0YoRiTl9T1UkMVgzMwlkf8bRUIesOvY6n7"
    "RO+fF1+BCjNYP72B3nrE+ZmT/cRyxhfb97WDROaAB/2DNH9bQhvHVFHSQHiayy3lKNDvI7T7bYS4N0jUfy2XPQ2AX8z1RHJ4UtbQK3GpiY9sDNqj3AN31YnGgJOcLCzYp3iGEdZHlXe1z1WIGq5J+Rvqrxck5xVhTwnTJPWn9b6Tni/ixHfiYyezWBVP605KDum8YmEq"
    "iPoiE+D9FxfX4WXl7MbK5yEoeW53p01v/Jca3YVLkIvnF3MPYR/WAHtCdWvNgF/QUQTJ6Jf8VSH+etyX7Zm8EikcB6agnKS5vl1aaMt9h3sAcC7jcu8zGhOC0kUfB/VS/aFoKsYyGjmlzlJ6BlSPj2sRjZg5ox9n1Wp0e+jvXp2oWrhqBD5XOWbgqTZaKN23C6LRLvdh"
    "rJ7NozeDtVIxxN9qGBZGoNwYiOhLKcStDYBf3MG2/OcCiCm35XH+vZwxu7Xph+UZJPR1pJngpY4E0A1SKeK5HDe+A0tnOqibk0cdvYL/nQhmgZSfWuC32QaUWFvcDyqxqcWDgigC+tIEKAnRZKhs242deNul4oN6AcnoNbfLTmnW9J+DYg3J2WJU3tAq7VtWkH0jxxvz"
    "TGIxOs2AX+mkp0v+4nOmVpNAK6BO90DLcSLVr1Dff3cLdeu1wwictY96acgaKRakvCkvheooGuTZuFnB62AsfxklFmVIJfnS7I4BZgrVeBAEVChZZZEAqqL358+c4a7aG7cp4DA04LlOSv0YKbvssbqGTfT+Am0QNX1Q1xMXPep7vr1RWS9NgF/IYLaJBYvmGgLTnkww"
    "hoAeXCc6uuZo3IwWr4MDX1geBBag/agKW2u4QaKR90cVan0ybL8aePv1EuBAo6WPfgbUEsDBBQABggAj9B0kmEAjVT0AIvRDIshGPVcXgF/NJPgjLchDKawYLrRDIAJUAYgUKnxDBJjZmBgAABQllFYojEMoUkMADSWgVj3IAnAXL1RDxCwuTEM8xAIixDIoGCgrFEMg"
    "QZxbCYH+xRDljYBf9e2qCyASnFsD2N48k3/ALJxbIAT4BCidW9gilIciliYbWyucWwDzAlOQmQchbY5QS9gmUliJdjIn6rHrwlUanfdzIzeR/P0xPFrfBSf6INxtgNWUijQajcYe+0gxQvZQ3GUwjsXf8mgsGrEDmYYpLh6l6YV0s5GtDGj1g24gioEjFDoRz46CPqGo"
    "ypVilkR7uWk9F1dsTYBf2RlprNOihB9DlAsT+YJ0mNwyWsMolpYKVIyw6oxQ/5pLgY9SF739a7nG9LS85Y0r/xE2vfdnpzOb5zSXcv6diuq2SxFNONPRu1RRRxA1pS2hDFC6w/WHCg/NPyF7g+UimqW/zGlafinKRkbN/Uad7EFkCwHeRJSVHNfeT3LzHs2AX/uVn4DU"
    "EsBAhQACgAACAAAtMeCieNeUASAooFsiaKEBjYBf3Sx0oS4YTS4wQ5ohAAAgFqFbQCigWyLIWVTjKDg1Lmw+thsGQCRsUGOPnhtbLpwCLsQ4tQ4tIoBOKLSULuAAIthlKhA3IiRPog8WgSSgWyAEhAs2aAI5oVuBI1RVIniOIAaEASPAMi4JA8otbC2rLwAbgiSoUz90"
    "AQSAX81REJCLKbAtsBko6BSQFiKoF58CAAAIJQhaP5ABVBgt1BcnZFgEDYBf7ZwYji7oF7YZHYNsSiAFZTfdKiEYlFyZIzRlMSQDKAQbV6IAADQl1F4gBDADL0gYqDMiLK8uUBi+MglDcLMtkAEBDYBfzjOkQCuIGLBmJKxELkQWuhkCRCAG9AdQZiN8FgFNgEjcIihy"
    "uLIsoVsYKKBbAA03/20WACsTwIBEpAZCA4BAQAPAQEAQFggSEAiHMG0VE3ZGRGTIBgYUAhAIh7lp5RZSDWKkJnRcCQAWgC1WARqAQAkADiKYtyJgtyKNXEAiJFwDEYAQQBGAJCu4EEAOI8VcECLZt8AkxVwRIqC4CUAMQA4ADkANABCAECLcXCIIbyKURiAAdii4AvKC"
    "J3/7NXRcABKgzAQRa9izbYy2EAgIOMogvYEvYBlO8RKsBG2qx6/JiFSu+tokKLgAt12+p7v6Euv3jjbA80IIG2lU8ZOPcRwwUdAJ85W58IvGyArZt3DNgF/JgNn0+riskvS2aBtSKp1Su+i8F4HQPKemh68vOpZZCKG5PC3bBHyJiad0VeX4BiNQs8jRqV95mL0Cryux"
    "3YoxhIPZUVx1QwEt/W5weOZfNT1UL43RcPyDeYsmPl1X65aBK2AF4S0mFJMik9adeTQVYc3cuwIYflm/wPFRf0TijYBf8aGstjffWIeOE2PPAac5VsWqTyCSnXLjf8AUEsDBBSBvdFwD2j8C3JyANi241iNUggAAZCK5d8KbB6BJDKOItKeoBdwwKEoYCNjoxy/yyNKU"
    "6VV+lU+wJrZ9c6MMdtd2gYNNgF/0vS1VhkOfIqRVIUua1Vl2NmTt8Zox5nR2n4pw0iJVmZ4hDFnldGuW6BCKyuVBVTpUi6g6HtpMSoaWGS4Lz5kK3zhLFT0Z78TxVlU0g98oKGOs94aEIDmIeMb89PxwsiMc+ZcXS5sXcK0+lRLg3mSHDZ5eIi8PIoDL05z6m2SfTYBf"
    "+od9vQtSfLoNQ1TRsZmzmzdXtUVRgorS8xDSjdeEHg0fA/iLV1t49ULXW8pZWQsv2tyXflkk6uVjcJF7tzWYx6AkIn45hYisqgXA+ghnJExRPhMCd8HDYFAyFYcm6uPM0CDLKw2MTCldjdqEI2TMJX6dHrQzwtG5k6YOm0Orh82AX/OCJ+e8fuOcNRCVWBCWFgenR11s"
    "lnDElonjTfYC1LatKJ5zsYvDv9E3cQ/lFToRpv/UkSWAyLL70HG+8g/AVBIqjLUDw9x3bZ+AIAEwuABjKVNtz9QI4a7j1gWNgF/MtNwOXb5q9HBjj54+HhV+5kDebv88ilq4CcGxMVHGnycNJR1pAikNSqntP7dgMR+dhp2BqOmnMpy0ODGvoR10+Dj80CUKOprJ6hAe"
    "aeCiZqi7Bp64+zML9hYyy1URlW/0rZ72HwBUJcA1JHAaAfhNLT4SrkAEgCNKfwxAJEQaABTODU4NDI3QTQtNDg1Ri00MDQyLTg1QTktQzEwMzE2ODlFRTFFL2CKdMJ4ikDArNLgAAA+pCTCRFGVnqAXIIakKDFYPKocv1A7UvuXHxbNzswOrNjfxxv4NiFa73pIGgyBc"
    "YPX1l16mNMZcQj2UjYBfwTv0x8aBE6NpocVhlJcgs/TAg3eJeNSQZ3XZgFVjCZBMNzKpYdx+DKjalROhRGvzaSGq7qYhjSlXXhSxBRKADAPqSeUnHHavR0oopx9IIpphzg7bNE7wWuy4dvjkRxFOwulyNnqRW51iWPP1oRnTapYimTHR/whGJWMhrLDeIs2AX8IQbj7J"
    "HSH2Y6yV8x3GIu20v+J8qSfFGXr0rpb4s6yCCUR7dyQQvt8uj3CmPvkQwJ13iqa4QVK3GDMCOOinYnl+cVxQxfHmHwo37u6ngqXsNl2Q6Vo64ZK+V1fqXWb8gdTsXy7tKRkiktKeCyAG/AUjtCkgLzC4Ac2AX90gXXhcAs2AX/e4IFx5XM0ksNoo4DMB1kz1CCJ6XA7E"
    "KDC4IASQBinELgAAAAAAAKArVdbb6M4FP4riH0GQpNOmxVllCZNFY06U03U0T5Uigw4lC1gZJtOur9+P4MhNgF/QJJO9pKHgM3xuX7nYu/zLkuNN8pFwvIb07VHpkHzkEVJHt+Ypdxa16bx2fc4Y7JDZho5yeiNqbZN34s5Kwu9FdEtKVM52F3e/mGIkObUNMKUCHFji"
    "vCFZsQmpWQRFa92RCSx4+3Odu2asM825qR4GTAtCKe5hKbYz8HFqJVy+zYBf8uR6fieo777nvrXVOPTVE5lT19+kgtJ8vBA2IDN2J0s7i4up9blZDK2Jp8uXOt2ebuw3KvxaP5pPp/O7qYQLCQHJ60Jp1vTv4dveBJ6Tv2p1VgrfkylkOU5DSv7YWGls+YY0YLmEeKYU"
    "AFpHatH/aWrfNP5PFZrLbK7fZ5V3RM2AX8dRo3uzbOrKQv+hAniHFRwQRWqav9oQ2v8jfZeCxhL9bdEGBmRlCckNdIk4IS/mz5IFYnv9dgodHKFcGWB6bt7fl1dkRq/xu4xLbdlmipomn6F7A3wT6WoNEv+ovy4NOiEWJVJLq+1QfK9oKY/9Zxq0/fUY3yhP9aONLYpi"
    "RFyNgF/mFl/HRg6V7m3Wpj+l2WwW6t8PC684KygXCr4AFpN4Jqn8pIW654VOXUAxvR8vnfKd3j+K9J3rwrixpPdZDfRUiQnudgyniE29qj6GaPmxWrfDl9QzwbUhzTtzr8i9pxW2X7BOBU/gEuF5vq/x6/vsy5SO+HzvTckGONj7cp1SDYBf1KUnockR0AUKI2UYQu1f"
    "BvsTH+FSonKjlMk9VuHHLx4zhu+47/mjWpVie88cwR0UG/PqPzwZZUW0O0EWA7qZCVYG3fK55f/S87MFusv65JvSUgfdGFZ0G2SJxK9cw/erkK9QPQseqXvPxmPYOhhENbdIGRalIC3lc+V4+OmWag2AX/FXnJPQIhzMVM1z/uFhIdEhDRNSU5Z2Uhp25DCaltk9JyAL"
    "KwdOr4YoJjTt0RNEj2Knlro9SFPCuWytum1ddo+YcvT6itACfqUBSTdEwX7ah+ylPFN8L6pC6EJ7OFIH9w/+ujWDnUUFwC+gnJTcbSHN1Gy3ZYCZfeIE3+s5t1ANgF/tXXk8KXJn0ZinZITFGekHuEavY1MzAOcoK+zfJOgiyMrjwrvyh4KEBXfE/yDMis2JGNlLs9x0"
    "6ixp9G+Zd4dYsRPIsMX019XT+sWFTui0T5UPRCoDnTEpl54prfLy9HV3Z21nC2vrMlsOrVm4/HCmtzdXbrX08ntfIIu10+ApjYBf0F1UxDeREP0Sp5oNz+t9llr+g9ECue+zicnrp9PKxtTsefgDPDdHlxlRUozmkui0PugXtLvBENFj0e9v8pITM/g8u1+PdABO2ece"
    "1SZRn8OzurducqFo0zkS5kFOUnSwUFtuF3ksTa7cWX7rAt6s1Qr7U+MoYKlSYR6ExkxZRk2AX+VqDpnFHueUQHEdIfySF8ezjj9Vo+DkgQpbTR5IZiIUwFUA25lKPv7xm+Y4NQQdWOi19mv+NOJaBoI9Y2J8iaTkAo7QHdUc0/FHBDAENbWQICe5HGKwbo+1K7bU8o3K"
    "D9ogFp+S3LOsKTt6tXdjBQFmnavqla6aQHhPzK8UccgNgF/Eq9BKVtb9hutMZUYH7UG5rQPTBCvWvQO+fWxWa5d0fQ8ctY16UMQ1FwtSXhcXQuU07VKs8Wjg0nAWH0zirSMEcvzOVmcAsylSnCgCKjQPAsiAdX578+PnOEqmhnLBBB4nrMsY7lezPRV1li/4GIaPaMsU"
    "HX7EBcj132uhn59DzYBf9kERFCbROIVG03CKQsGWAMgD7qpvp05KgYD8tXC0A1jAqYVaA9m0voWbiB51MVRpUq3WBYfzv1ORQoUcEzs/t9QSwMEFAAGCAAAtnBiOwAAAAAAAAAAAAAAADUAAABmYngvODU4NDI3QNesjgF/NJfQjLaBEKbBZLoxEIrBZIASsGCtURDV4"
    "XCQURCQMQSZ4XCAEcAEvLETELC4kRDvEAiLInykUKCvsQyBFeFwBzYBf5SAWGLgB9mjs2S4YuCAE+AQj+EUjGLgE2NvcmU2AXyJ51yMqGLgAbwdAgEZRxFpT9ALWGZCrQQ78qfq8WsSKrW7bmZG76N5euL4tdyKT/TBODsAKykUaLWbjJ0HSPFCDlAcpfDOxV8yKKxac"
    "IAVBilm79J9g7SzEW3MqHUTbqAKASMU+paPAYL+wEWVKsWsCNfyrvRVzTYBf1iyMtNZJ0WIPgconk/WCdCR4XABfnqyUqRkpk1jpvzTXAx6kE1z7kZ+5mTc1YzU7UhJ15xacj7Rt6YZd68tb0W1mqWIZvnJqD2qiBNITmlHGCOUv7O6p/u+3r/QQ0+pqFb5H1O6T/80J"
    "WPjjm9xn7YAkuUgD0KKau0rr0eZeTYBf6/dym9Qj9E44LEd4qpQBIE50XC4wQ5ghIDV0XC5sPrQbPnRcLsA4tg4tQSRENjUMtQL4TYBfzScJNwAi/Da+DhcBJHRcIASAC1i1IiTHLvhSLoQyuhc0wSPEVyJ0XCAGhAEjvDIugAEuaC2yGBvCfD4+dAEFTYBf0VFMUUsp"
    "rC2wGTFMWSsJYQklQFk+kAEjyDst0BcnOFkgAXRcJQxeIAWUASAZdFwlGLggBJgBL0QYqDM9dFwlGLgtkAEiQL4znEArhBiwZiQAQi5AFrR/EjCYOyAaKixCI3gWIAZ0XAUWC9IQCIfPRCV5XOQpDFwFFggaEAiHJ9l6BkUk6AYADCIQCIcreawAP0iAgLDkBkBk/kJQ"
    "KQOpApAUBkCQIBIUnwAGAPM9AkFXwB0AGUAeAB0AEOJQA8AFwAXwExxAD0AEkAZAB4ACAAMAA+ACUAqkVRJeLRgBEASlLgEW+Rh8E5NvUAEQEp8fApF0EgsgYARAXBIMBJAEUATABEAFQARQBYAFXAQACjAEgARQBDAEsAUwBVAE0AooBMAhAWEZAWJ/jgNyLLIkMcMC"
    "AAD3IGvAAgAKY5kBZP+LgRoCCUiAgLEqpP5G0CpBEeSQBuAHMBKcYgEHQAaQEnykAgUABvAGVAUJQAAACRFBJBEeSQBuE0BIDXIAdABpAG8AbgBQAG8AaQAS+EAPAACkBQGkEQQxAAAApBEYPwBCExibCWMAawBSAGUAZgBJACII3AAskOQQBjAE8AYgBqAFAAcgBvAH"
    "AALgAxADYALgAyAFPXABBAGMATwBiAGoAUAByAG8AcAAuADEANgAuADIAICEBgaUAYwB0ACgAPwQASGhAROQMwkBJAGQALAAxACkALgTjKYS+EcIyAHQAaQBvAG4AUAWSDQIAIABcAGYAIAAiAASUDkG1ADIAJQBwAHQjQHIjAEADcwBbAFgAPQAgACwAXQAiAJFSUAb"
    "AB1ADIAJQBwAHQB+ARyAjAEAGsAWwBYAD0AIAAsAF0ApEk8AYgBqAGUAYwB0AFAAcgBvAHAAZQByAHQAeQBOFdd1pFE8aDpgNJM8AZQBWyzkATxYJHsuApGkbEwDBlAGMAdAlE52aweQErxnpG0CMAdAByBcbQAsBnAKRpPAGIAagBlAGMAdABQAHIAbwBwAGUAcgB0A"
    "HkAVQBuAHIAZQBzAG8AbAB2AGUAZABJAGQAocDcBxkt6h7JqIOx5CMRoidmHZDl5CEBYiemHQCCmeggX5SgAGSAAAAA2JAAPAAAAAAAAAAAAAAAAAAAAAAAAEQAAKSO+cP4HAE36ZEH8+mRBq/pkQUv6ZEFL+mRBSuiE7Jr3RfAHAAAAAAAAAAAfAnQCB6OOJQD4iXYC"
    "BDJ8A6UBZKQCgAKADIQDAgD/////nAIgAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAO4cAAwAAAAAAAAA"
    "AAAAAAAAAAARAAApI76E4WzWrlJQ/QcAbvlkQfr5ZEGr+WRBa/lkQWv5ZEGc+oUlFPnDWAMBAAAAAAAgAAAAAAAAAAAAAAAAAAAAAAAAAAAAAAAAAAAAAAAAAAAAAAAAAAAAAAAAAAAAAAAAAAAAAAAAAAAAAAAAAAAAAAAAAAAAAAAAAAAAAAAAAAAAAAAAAAAAAAAA"
    "AAAAAAAAAAAAAAAAAAAAAAAAAAAAAAAAAAA/AAALAAAAAAAAAAAAAAAAAAARAAApI76E4WzWrlKQSfHxu+mQ/QcAr/lkQer8ZEEr/GRBq/lkQav5ZEEPrCZ9sKvGiQAAAAAApwSKAQQB/dEAAd4AAuYBARIBDQELAQ4B1AYC9BIB/f4AAfj3QAGtggEBwF4B6wEBtgYC"
    "+kEBIQHdQAGQ6kABjYIBAeaBQQH2QQWRdwHkmQEB2IRBAZScAQWjSjHhkUEB750BAfdWASsC1F8BgjcBjR8BLxLcm0EBxvgAE+DoQAHv/AANtGACxhEB5UABygEBv+5AAcINAdsBAe8BAeIBAfnzAAHUQwGu3EABglIBtk4BqRUBt1MBpoABAcTjQAHoTAHDTAGVRw3e"
    "UgGWggEgwINBAd2AAQStWQH8BQElAS0BNQHqAQS+EQHDMh7GBgPo2UEJ2NgBAZ3hAAFbAZ8uARsQuMVBASIBIgHOgEEBIgEkASQBJAEkASQBJAEmASIBIgEiASQBJgHAAAE+AT4BPgE+ATwBPgE8ATwBPAE8ATABwAABOAE4GqLTABavewG5AwGCUAmWFwH7AQG2BQGr"
    "SQHjQQSrjAEBvzMB5XMB+AUBi9wABM+2QQHQzwAF7QQRpcFAAaiWQQKyLQLg9QABrUwBmzyEAaHvQAGd1gABHwGV1kABqNYAASMBNAE0Af3WQA+tHwEyAdQAAZwCAegAAd4AAcOLQQHikwEB6QEB3QEBkI5BAegBAdUBAf4BAYQCAa9NATYBJgE6ARgBMgGCsQEB+UsB"
    "si5H7KpCAeq5AQGW1wAB4h0BtwEBPgErAYBaAYQBAYoBAeQBAdAAATEBOwE7AbkBAYkCAdkAATkBOQHXAAE7ATsBmwEBgAEBOgGG60ABGgGB6wAB/goB7YsBAeICAdqDQgG26gAB9goB/YwBAdAFAcuyQwHBAAHJAAGxAgGxAhTLOwHsBAEyAcIAAToBMgHcmQE/7UYC"
    "4X4n4tNAxgGwwkABx6UBASUBNFj32EAB8AEBygEB5AEB9gEB7VE+zPsAATAB5tAAAe4KAYr1QQHOAAHSAAG8mQEB788AAYXoQQGnAQHEAAHAAAGXAQHIAAGfAQHAAAH8AAH8AAHCAAHSAAH8AAHEAAGMAQHUAAH8AAHnYwGtlQEBmZJBCRMB4JMBAf6QQQkTAaWSAQHL"
    "kUEFEwG0kwEB2pJBBRMBwJQBAbiTQQYTAaaVAQHMlEEFEwG+lgEB65NBCBMBoJUBAbCTQQgTAZeVAQHhk0EB/pMBATMBMwHllUEBKwErAT4BypUBAfCUQQGNlQEB+QABKwHclkEB64QBATsBOwGFlkEBPwGBAQEzATMBw5QBATMBMwGolEEBLwH3AAErASsBgJMBAYkB"
    "ASsBx5NBAY+UAQGGAQErAdOUQQGblQEBMwGGAQHklUEBKwWGmAEBOQE7AZeXQQGKAQEzATMB+5UBATMBMwHrlUEBNwErASsPyxoBqNwAAfjfAAEkARcBGwHr2kABJQElASkBKQEXARcBFwEZARcBIwEXARkBFwEXARcBFwElARcBFwEXARcBGxKk60ABxgAByAAExgAB"
    "hAED8lUByZYBAeeVQQUTAZGYAQGvl0ENj5UBAboBATMBpJhBAfSYAQG2AQEzAeiZQQGTjAEBkgEBKwHRlkHKBQACAdAAAAAAAAAAAAAAAAAAAAAAAAAAAAAAAAAAAAAAAAAAAAAAAAAAIAAAAAAAAAAAAAAAAAAAAAAAAAAAAAAAAAAAAAAAAAAAAAAAAAAAAAAAAAAA"
    "AAAAAAAAAAAAAAAAAAAAAAAAAAAAAAAAAAAAAAAAAAAAAAAAAAAAAAAAAAAAAAAAAAAAAAAAAAAAAAAAAAAAAAAAAIqQAAwAAAAAAAAAAAAAAAAAAAARAAApI76E4WzWrlKQSfHxu+nrs6bbPIcMPpkkXg0cBrdHEOcHACjjZEF872RBq+9kQSvjZEEr42RBJhI3ZDgO"
    "vQ0AAY2hxLjEqfjFwNz0X+fPtoqlEgBgAAAAAPgnlQAABgCAACegDDzAUBRZKqPUBh5gKAoslVHsAw8wFA0WSqj3AYeYCjaKVHwAn+HjzAUBRlFKPkBIEEHmAoGi6HUfQCf4ePMBRlGqj7ASBBB5gKQo2gNH4An+HjzAUDSFxaP0BIAEHmAyNoDR/AIAgg8wGqj/ASBB"
    "B5gMjVQAAUPMBkUqAECh5gMilQBAUPMBkUqAMCAEEHmAoEkLi0AgEAIIPMBQJIXFoBQKHmAoEilQDARAgg8wFAUZTegHAiBBB5gKAoym9AQBECCDzAUBRlN6AkCIEEHmAoSjKKUBQEQIIPMBQJGU3oCwIgQQeYCgSMpvQGARAgg8wFAUZTegNAiBBB5gKAoym9AcBECC"
    "DzAUBRlN6A8CIEEHmAoCjKb0CAEQIIPMBQJGU3oEQIgQQeYCgKMp7QJARAAg8wFCEZRSgTAh/CB5AKCJC4tAoBACCDyAZIXFoFQIgQQeYDIynVAsBEACDzAUBRlFKBcCh5gKAozUDAFDzAUCRdDKRFPAGIAagBlAGMAdABEAEIAWAAgAEMAbABhAHMAcwBlAHMARlBAG"
    "MARABiAEQAaQBjAHQAaQBvAG4AYQByAHkAVwBpAHQAaABEAGUAZgBhAHUAbAB0AETQQBDAEQAQgBEAEkAQwBUAEkATwBOAEEAUgBZAFcARABGAEwAVABEU8AYgBqAGUAYwB0AEQAQgBYACAAQwBsAGEAcwBzAGUAcwBD0EAYwBEAGIAUABsAGEAYwBlAEgAbwBsAGQAZ"
    "QByAEPQQBDAEQAQgBQAEwAQQBDAEUASABPAEwARABFAFIARFPAGIAagBlAGMAdABEAEIAWAAgAEMAbABhAHMAcwBlAHMAQpBAGMARABiAEwAYQB5AG8AdQB0AEGTABBAFkATwBVAFQARFPAGIAagBlAGMAdABEAEIAWAAgAEMAbABhAHMAcwBlAHMARFBAGMARABiAEQ"
    "AaQBjAHQAaQBvAG4AYQByAHkAVgBhAHIAQ1EAEkAQwBUAEkATwBOAEEAUgBZAFYAQQBSAERTwD4YBgAHEOQQBjAEQAYgBUAGEAYgBsAGUAUwB0AHkFQCDgQpUAEEAQgBMAEUAUwBUAFkZAIDEU8AYgBqPHgFARBAGMBYVwAgE0AYQB0AGUAcgBpAGEAbABCE0AQQBUAE"
    "UAUgBJAEEATABEU8AYgBqAGUAYwB0AEQAQgxKQUPmFIAJFYAaQBzAHUAYQBsAFMAdAB5AGwAZQBC1YASQBTAFUAQQBMAFMAVABZAEwARQBEU8AYgBqAGUDl4BQAYJQQBjAEQAYgBTAGMAYQBsAGUAQVTAEMAQQBMAEUARdBAEMARABCAF8ATaBQGEEARABFAFIAUoBkL"
    "F8AQwBMAEEAUwBTAEQSIUgsE0ATABlAGEAZABlAHIMpTMTRgUAQEARABFAFIIA1JBUSYVA8QwBlAGwAbABTAHQAeQBsAGUBQWQAEHAAQxDAEUATABMAFMAVABZAEwARQBFBbCQAEIRQBYAEEAQwBfGxxBFwBE0UAeABQVQ9YAFIARQBGAFAAYQBuAGUAbADsdgA60UAW"
    "ABBAEMAWABSAEUARgBQAEEATgBFAEwATwBCAEoARQBDAFQARFPAGIAagBlAGMAdABEAEIAWAAgAEMAbABhAHMAcwBlAHMASVBIBaBCQBtAHAAThksQADQAGUAcgBzAGkAcwB0AGUAbgB0AE8xIMEzAEMAbwBsGhlAowB0AGkZA0JDU4AUABPAEMATwBMaWlDr75EU8Ag"
    "CL0LBFgnB5AGUAcgBJAG4AZYagaABC0wAQQBZAFQZwJ8ASQBOGJqYAEgAsQLqGcBFMAcAFy8fLsMEkAbgBkAGUAeABDVMAUAbL5svQQF8ASQBOAEVsKABCACDQwMWGsAFEQAYgBJAGQAQgB1AGYAZgBlAHIAQhJAEQAQgBVAEYARgBFAFIARIALdC1G9vZRg3nhWClgB"
    "pAGUAdwBTAHQAeRoXQoUQQBDAEQAQgBTAEUAsFoKVgBJAEUAVwBTAFQAWWBhIALqBRE0nMdQWyK4EQOQBsAFYAZRYXDEyQFNBAEMIyQQVMkiABIIJAEwAVgBJAEUAVwgDs0MUCUYEgMUwBvAHIAiIBIJG4AdABzAFQAYQBiAXM4EENUwBPAFICJIEgEE4AVAXM4BBBAE"
    "IGTPIAJZBg2bZUUAdiNYEgxHAHIAYQBwAGgARVBAEMAixBADF8ARQBWAInASIogSAAIVABJAE8ATgBfAEcAUgBBAFAASACADBQ1dmGwMCAGwAbwBjAGsAUABvAGkZM0IQAGEAcgBhAG0AZRk0gPIARNCAExlyUtkywAGSQBOAFQAUABBAFIAQQBNAEUAVABFAFIAIALa"
    "BhD0mG0idBgAAfAGMAawBYAFkARwByAGkAcABC0ifBgOPAEMASwBYAFkARwBSAEkAUAgBMwMmGcJEIAbABvAGMAawBHAIqQYCRwAEUAeABwAHIARpFhiBPAEMASwBHAizRgFIkAeXAMiFBkKkATwBOAEMATwBNAFAG0CUFBxIAM9DROQbg5CAGwAbwBjAGsATQBvAHYA"
    "ZSNgFAh0AGkAbwBuAEPQgCOyE8ASIgoYwBUiyRNAItATcHEgA+EGWTDgBl3XyGhqAYwBoAFcByZxExK4bVzWInQWBFQAQwBIAEHE3yAC0gYRZC/QBgEEYAbAUGwMBQAGEAcgBhAG0AZQB0AGIgEUSbtwGAEwaG8LQAEEAUgBBAE0ARQBUAEiQBQgAxAUMUAHBIAbABpA"
    "HACSdhDUsHQEYATABJAFAKB2IAK8DTHYBgRGAGwAaQBwNtgGAxGAEwASQCLkGiAN2QZhWGUiaCC92zBl25Rs2jDFDRS6bkwAXdtFZNsgFMwNKKgUr9wEwAYinRpQUG+t3j2wblttOAEUaG0gCg4OR5AliRQRIjAhBoAYQBtAGkAYwLTkAAIUAB1AHIAZwBlAFAAcgBlA"
    "HYAZQCIQFSJMJwMSdBAEMAQixh/wBCLIIQbgBBAE0ASQBDAjABVU6QGwBQAFIqwnCXAEUAUABSAEUAVgBHzoAlAFIAXwVAMCBSAFMAR08iACAQgJn+1GAGkjwCIEZABBUYASQCJQIgIRABcVcFi4AAEGUATwB1AHQAfABQAHIAbwBkAHI3MiAgAEULwFMAYwA6ACAAQp"
    "2CIBAgAEUCLwMSQELAUHIAIABmAG8F0BBeQUBwIABlAG4AdABpAijCwCAgAHwAIiqCMI8AbQBwAGEAbgB5BlFhBUH1wdIhMvBrACVAlXbzAC4HwMBgVwBFAEIAIABCKTKEAHIF0JB2YlB3BXAALgBi4MAQbgBjAG8AbQBC2QpgANXAGkAcABlAG8AdQB0AEHVwBJAFAA"
    "RQBPAFUAVABEkDXtKhcpxioQtCaVENAqxCoHBC00AVQBMAFQASLkHViUIiUeSCADShdG0IiTw5CAGUAiKhcZQCLgN1iOJHgkAhvAG4ARI6gkARhAEdSwkid8EGiLcI0iZyvgBUAl+CQD8ATgBfAEdQMQIAOwFyeUHrGNTCMrMXQAQrCPI5wQA8AVABdyIPB9PBoJAgB0"
    "APwMapogByIkLAIQBwAHACLsFQEGMAYQWI4EBvAG4AfABGhz2I18EdUBBC4QCMKSB8A4EAm8EFKTB3A4OwkCIAQnMCjxlFgjnBMCpAGEAYgjKyjMARD5mFYjfBMBSQBBACLkEwRFAFMAYAiAJpQyCREAGkAbQBBAHMAcwCJqHx8AIvgQChvAGQAdQBjAHQAIABEiWDgE"
    "wBjADoAIAJQAdA9VDggiUDUk2EBUj10LgCIMJ1wNXAciEBIBHMAaQFSRBR8AEMAbwBtAIuAtARuAHkDUFJQWXBMBHUAdAFQgVKIDGsALAAgAInguCRjAC4AfABXAEUAQgFcJGQAZI6ATVC72Eh3AVAABC4AYQC0mAYAYbB8BCIAQxJDUA0AGkAbQBCQANAAa8AYwBCEQ"
    "ASQBNAEEAUwBTAE8AQwABABaJ3ZYcl47RztWBzo/IwugGDBJdQAj8EogAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAFwQAAwAAAAAAAAA"
    "AAAAAAAAAAARAAApI76E4WzWrlKQ6wcAqe9kQULvZEGL7mRBq+9kQavvZEEx+EZly/sSIAAD/3cBIQDFAAAAQwAAAP////8uAAsAUAADFgAuAAAAdAEBBABlBV8EAAABeAGUAQ0BAQECAAEAnY4lAPiFUwGjXAEBiXYC1IcLAAA0ZAqUDVwYYAQBAAAAN5ACIAAAAAAA"
    "AAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAC+HAAPAAAAAAAAAAAAAAAAAAAAAAAAEQAAKSO+hOFs1q5SkEnx8bvp"
    "67Om2zyHDD6w6gcAiu5kQeHtZEEr7WRBi+5kQYvuZEEJCS4/sQ09nwABz3sfI/3eOKlffGi4Tm0zXwoDAGIAixVoAQA64AP36roStZpDRATMC0CQSkBgwMDAwAAJBR0MDk1TaqQhBkGQZBkGQZA1GlAQSTJJqZmZmZmck/JqZmZmZmak/JqZmZmZmbk/qqqqoGAUACQD"
    "gP1J2OJQA+IVTASjjiUAPiJdgIMDAwTQAAAAdDAwMDCHieBgGHieBgGAAAAMAAAgXUqqqgBoDi4SAChAdAQDIkCqamqqUAAAGDVpYRnfbhCQB+Ee3ybHgmQIlMIVRVycWUAzgWeHv6zR0ADT2GEh/iakAHQOLRYAAoRwBAICJAqmplwTB6kCtejcD0Kxz8BgBgASCwPx"
    "SuB6F61HYPwK16NwPQrHP6pBgtRFT7Iek/oAAAAwQAyqpAwFrXo3A9Crc/hcQQJmZjlAZHgMDLc/iBBAAAAGCAQAAABggHgCCIIgiBIFSBJdQgNRil8FlGQcAA0AAWUA/v8/v9AVGB0qAABAZ/AAECAgAAQEAQEAAEhSfggAIH4BAwh+AQACjAECkoEAAIBvAhoH4GwB"
    "AJgAggAwWoip9kPyfgwWoip9kPyf0g4CexQuR+FyoSAeFPjJZvMr2BGBwf/+AgIEAYAQAAwwAAkBbQCpAS4AqqSZ7AEUAOQAyADEANwBGADQARQAtADQAQwA5ADcALQAxADYANAA3AC0AOABGADkAQgAtADIARAA1ADAARgBEADkAQQBFADIAMQAxAH0ASZ7AEEAMQAy"
    "ADcAOABDADQANwAtAEUANQAzAEQALWQBACg0AEEALQA4ADgANAA0AC0AMgAxAEIANQA1ADQAMABDAEQAMAA5AEUAfQCHAWoiCiIqIqoyyiTqIwoKZgAiKmgBAEAKBiAmIEYgZiCmIMYg5iEGISYhSiGqIuYhiiNKIyohyi5KLmozKgorCiPqIqoiiiLKNGo0CgXqQUVg"
    "PkqOhhXYeTCE4NwCIcdWoIOXR7GSzKAAfFIgAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAAEFAAOAAAAAAAA"
    "AAAAAAAAAAAAAAARAAApI76E4WzWrlKQSfHxu+nrs6bbPIcMOwBjQTQGAAD0AQAAAgAAAMOEiZMHDgAAAAIAAAAAdFIBAABcA3QChAEFdAAAAQAAAAKIAyAkGQASdBFcFVwdXAFdFw14BQAEAEFjRGI6QWNEc1Byb3RvdHlwZV8xYowGIAMYAAMFAAAAWQm1CuBRBAB+"
    "MQAGfAFdHAyICHwbCnBwSW5mb0hpc3RvcnmEBiAFGQAEWQkGUAF9AOJQM50bA70bC3gHjDd8G4gEIAwZAANUC2ABUwIAADndNwi9Gwp4B3wbBFByZXZpZXeIBCAMGABpMwi5DFaIAl1QgIw5XAKYXGxTBFN1bW1hcnlcVIgLIAgYAFwSXBWRDBCAAlwF3IuYJG8bUmV2"
    "IBPsBlgWWW6cUAKOAJDkcAJsPc2/B3gFfFNQHQRPYmplY3RziAUgCBgAXhECQrgLXjF9Sb3gWYgGLrwDXClYBlgeCjpPYmpGcmVlU3BhY2VQBSAKDABdabfMC5wVLrwBiJV8OwRUZW1wbGF0IA+sAVgZXaGRUAKNAJBgzHyp3HOIBXwbA0hhbmRsZSAQbAVYGF3ZQZAv"
    "AQAAANc1vBGY0GxTAkNsYXNzIBW8ASIdEVdQAVAfAQAAAIGMAS48BW6TAAB8NwZBdXhIZWFkZXKACyAKGAAinRTpzQs0gDIuvAFsA5wbIBewAQABAAAADgAAAGoDAAAAAAAAAAAAABEAADsAY0EAAAAAAAAAAAIAAAAAAAAAKSO+hDsOY0GAAAAAewAAAAIAAAAbC9k1"
    "DgEAAACgAAAAAgAAACAIAAADXAEBAwAABFwBABoGAAAFAAAAgAkAAAYAAADAAAAABwAAAEBCAAAIAAAAoEkAAAkAAADgAAAACo0HC1wLAQUAAAxcAQEMAAANXBEBAQAADlwLAAEDAAARAAAAIAIAABIAAADgBQAAEQAAOw5jQQAAAAAAAAAAAgAAAAAAAABoQPj3kiq1"
    "7xjdC/Hxu+nr36bbPIMMPpkkXg0cBrdH3rMSTchCu4umDQNafYnwJR9d1Mv81TFFOxMNiQoc264yMJpQ7mB4Nv2SSTL23n1J3L9PFPLkgmbQa8QwtyM7oSLkIpGd4Ysf2p8ae7U="
  )
)


(defun vl:base64-decode-to-file (b64-chunks out-path / txt-path f wsh cmd result)
  (setq txt-path (strcat (vl-filename-directory out-path) "\\vertex_leaders_template.b64.txt"))
  (if (findfile out-path)
    (vl-file-delete out-path)
  )
  (setq f (open txt-path "w"))
  (foreach chunk b64-chunks (write-line chunk f))
  (close f)
  (setq wsh (vlax-create-object "WScript.Shell"))
  (setq cmd (strcat "certutil -decode \"" txt-path "\" \"" out-path "\""))
  (setq result (vlax-invoke wsh 'Run cmd 0 :vlax-true))
  (vlax-release-object wsh)
  (vl-file-delete txt-path)
  (if (= result 0)
    out-path
    (progn
      (princ (strcat "\n  certutil завершился с кодом ошибки: " (itoa result)))
      nil
    )
  )
)


(setq *VL:TEMPLATE-PATH*
  (strcat (getenv "TEMP") "\\coord_template_d057f5b8.dwg")
)
(if (not (findfile *VL:TEMPLATE-PATH*))
  (progn
    (setq *VL:DECODE-RESULT*
      (vl-catch-all-apply
        'vl:base64-decode-to-file
        (list *VL:TEMPLATE-B64* *VL:TEMPLATE-PATH*)
      )
    )
    (if (vl-catch-all-error-p *VL:DECODE-RESULT*)
      (princ (strcat "\n  ОШИБКА распаковки шаблона: "
                      (vl-catch-all-error-message *VL:DECODE-RESULT*)))
    )
  )
)


(defun vl:fmt-coord (val / sign abs-val int-part frac-part int-str frac-str)
  (setq sign (if (< val 0) "-" "+"))
  (setq abs-val (abs val))
  (setq int-part  (fix abs-val))
  (setq frac-part (fix (+ 0.5 (* (- abs-val int-part) 100))))
  (if (>= frac-part 100)
    (progn
      (setq int-part  (1+ int-part))
      (setq frac-part 0)
    )
  )
  (setq int-str  (itoa int-part))
  (setq frac-str (if (< frac-part 10)
                   (strcat "0" (itoa frac-part))
                   (itoa frac-part)))
  (strcat sign int-str "." frac-str)
)



(defun vl:fmt-length (val / abs-val int-part frac-part int-str frac-str)
  (setq abs-val (abs val))
  (setq int-part  (fix abs-val))
  (setq frac-part (fix (+ 0.5 (* (- abs-val int-part) 100))))
  (if (>= frac-part 100)
    (progn
      (setq int-part  (1+ int-part))
      (setq frac-part 0)
    )
  )
  (setq int-str  (itoa int-part))
  (setq frac-str (if (< frac-part 10)
                   (strcat "0" (itoa frac-part))
                   (itoa frac-part)))
  (strcat int-str "." frac-str)
)



(defun vl:mleader-style-exists-p (style-name / dict)
  (and
    (setq dict (dictsearch (namedobjdict) "ACAD_MLEADERSTYLE"))
    (dictsearch (cdr (assoc -1 dict)) style-name)
  )
)


;;; ------------------------------------------------------------
;;; Проверяет, существует ли размерный стиль (DIMSTYLE) с данным
;;; именем в текущем чертеже. Возвращает T или nil.
;;; ------------------------------------------------------------
(defun vl:dimstyle-exists-p (style-name / doc styles result)
  (vl-load-com)
  (setq doc    (vla-get-activedocument (vlax-get-acad-object)))
  (setq styles (vla-get-dimstyles doc))
  (setq result (vl-catch-all-apply 'vla-item (list styles style-name)))
  (not (vl-catch-all-error-p result))
)


;;; ------------------------------------------------------------
;;; Проверяет/создаёт текстовый стиль (обычный STYLE) с заданным
;;; именем. Возвращает имя стиля (строку).
;;; ------------------------------------------------------------
(defun vl:ensure-text-style (style-name / doc styles ts result)
  (vl-load-com)
  (setq doc    (vla-get-activedocument (vlax-get-acad-object)))
  (setq styles (vla-get-textstyles doc))
  (setq result (vl-catch-all-apply 'vla-item (list styles style-name)))
  (if (vl-catch-all-error-p result)
    (progn
      (setq ts (vla-add styles style-name))
      (vl-catch-all-apply '(lambda () (vla-put-fontfile ts "arial.ttf")))
    )
  )
  style-name
)

;;; ------------------------------------------------------------
;;; Проверяет, является ли полилиния замкнутой.
;;; Работает через ActiveX-свойство Closed (LWPOLYLINE / POLYLINE).
;;;
;;; ВАЖНО: vla-get-Closed возвращает не T/nil, а символы
;;; :vlax-true / :vlax-false. :vlax-false НЕ равен nil, поэтому
;;; его нельзя использовать в (if ...) напрямую — нужно явное
;;; сравнение с :vlax-true.
;;; ------------------------------------------------------------
(defun vl:polyline-closed-p (ename / obj result)
  (vl-load-com)
  (setq obj (vlax-ename->vla-object ename))
  (setq result (vl-catch-all-apply 'vla-get-Closed (list obj)))
  (if (vl-catch-all-error-p result)
    nil
    (= result :vlax-true)
  )
)

;;; ------------------------------------------------------------
;;; Автоматически подтягивает стиль мультивыноски из чертежа-
;;; шаблона, если стиля нет в текущем чертеже (через вставку
;;; шаблона как временного блока с последующим удалением).
;;;
;;; Возвращает T, если стиль есть в чертеже, и nil в противном случае.
;;; ------------------------------------------------------------
(defun vl:ensure-mleader-style-from-template (template-path mleader-style
                                               / old-filedia old-cmdecho old-osmode)
  (if (vl:mleader-style-exists-p mleader-style)
    T
    (if (not (findfile template-path))
      (progn
        (princ (strcat "\n  ПРЕДУПРЕЖДЕНИЕ: файл шаблона не найден: " template-path))
        (princ "\n  Создайте style_template.dwg с настроенным стилем «Координаты»")
        (princ "\n  и укажите верный путь в переменной template-path.")
        nil
      )
      (progn
        (setq old-filedia (getvar "FILEDIA"))
        (setq old-cmdecho (getvar "CMDECHO"))
        (setq old-osmode  (getvar "OSMODE"))
        (setvar "FILEDIA" 0)
        (setvar "CMDECHO" 0)
        (setvar "OSMODE"  0)

        ;; Перед INSERT — если блок с таким именем уже "болтается" в таблице
        ;; блоков (осталось от прошлой вставки шаблона), убираем его,
        ;; чтобы -INSERT не переспрашивал "переопределить?"
        (setq tmpl-block-name (vl-filename-base template-path))
        (if (tblsearch "BLOCK" tmpl-block-name)
          (command "_.-PURGE" "_B" tmpl-block-name "_N")
        )

        (command "_.-INSERT" template-path "_S" 1.0 "0,0,0" 0.0)
        (while (> (getvar "CMDACTIVE") 0) (command ""))
        (command "_.ERASE" "_L" "")
        (while (> (getvar "CMDACTIVE") 0) (command ""))

        (setvar "FILEDIA" old-filedia)
        (setvar "CMDECHO" old-cmdecho)
        (setvar "OSMODE"  old-osmode)

        (if (vl:mleader-style-exists-p mleader-style)
          T
          (progn
            (princ (strcat "\n  ПРЕДУПРЕЖДЕНИЕ: импорт не удался, стиль «"
                           mleader-style "» не появился в чертеже."))
            nil
          )
        )
      )
    )
  )
)


;;; ------------------------------------------------------------
;;; Индекс строки в списке без учёта регистра (0, если не найдена).
;;; ------------------------------------------------------------
(defun vl:index-of-ci (str lst / i res)
  (setq i 0 res nil)
  (while (and lst (not res))
    (if (= (strcase (car lst)) (strcase str)) (setq res i))
    (setq lst (cdr lst) i (1+ i))
  )
  (if res res 0)
)

;;; ------------------------------------------------------------
;;; Список имён размерных стилей из файла-шаблона (через ObjectDBX,
;;; без импорта в чертёж). Если ObjectDBX недоступен — встроенный
;;; список *VL:TEMPLATE-DIMSTYLES*.
;;; ------------------------------------------------------------
(defun vl:template-dimstyle-names (path / dbx res names nm)
  (setq names nil)
  (if (findfile path)
    (progn
      (setq res
        (vl-catch-all-apply
          '(lambda ()
             (setq dbx (vla-getinterfaceobject
                         (vlax-get-acad-object)
                         (strcat "ObjectDBX.AxDbDocument."
                                 (substr (getvar "ACADVER") 1 2))))
             (vla-open dbx path)
             (vlax-for s (vla-get-dimstyles dbx)
               (setq nm (vla-get-name s))
               (if (/= (substr nm 1 1) "*")
                 (setq names (cons nm names))
               )
             )
           )
        )
      )
      (if (and dbx (not (vlax-object-released-p dbx)))
        (vl-catch-all-apply 'vlax-release-object (list dbx))
      )
      (if (vl-catch-all-error-p res) (setq names nil))
    )
  )
  (if names (reverse names) *VL:TEMPLATE-DIMSTYLES*)
)

;;; ------------------------------------------------------------
;;; Диалог выбора размерных стилей. Возвращает (стиль-сторон
;;; стиль-М-линий) или nil при отмене. Последний выбор запоминается.
;;; ------------------------------------------------------------
(defun vl:pick-dimstyles (template-path def1 def2 single
                          / names i1 i2 dclpath f id res)
  (setq names (vl:template-dimstyle-names template-path))
  (if single
    (if *VL:PRIV-DIM-CHOICE* (setq def1 *VL:PRIV-DIM-CHOICE*))
    (if *VL:DIM-CHOICE*
      (setq def1 (car *VL:DIM-CHOICE*) def2 (cadr *VL:DIM-CHOICE*))
    )
  )
  (setq i1 (vl:index-of-ci def1 names))
  (setq i2 (vl:index-of-ci def2 names))

  (setq dclpath (strcat (getenv "TEMP") "\\vl_dimstyle_pick.dcl"))
  (setq f (open dclpath "w"))
  (write-line "vl_dimstyle : dialog {" f)
  (write-line "  label = \"Выбор размерных стилей\";" f)
  (write-line "  : popup_list { key = \"ds1\"; label = \"Размеры сторон:\"; edit_width = 36; }" f)
  (if (not single)
    (write-line "  : popup_list { key = \"ds2\"; label = \"Длина М-линий:\"; edit_width = 36; }" f)
  )
  (write-line "  ok_cancel;" f)
  (write-line "}" f)
  (close f)

  (setq id (load_dialog dclpath))
  (cond
    ((and (> id 0) (new_dialog "vl_dimstyle" id))
     (start_list "ds1") (mapcar 'add_list names) (end_list)
     (if (not single)
       (progn (start_list "ds2") (mapcar 'add_list names) (end_list))
     )
     (set_tile "ds1" (itoa i1))
     (if (not single) (set_tile "ds2" (itoa i2)))
     (action_tile "accept"
       (if single
         "(setq i1 (atoi (get_tile \"ds1\"))) (done_dialog 1)"
         "(setq i1 (atoi (get_tile \"ds1\")) i2 (atoi (get_tile \"ds2\"))) (done_dialog 1)"))
     (action_tile "cancel" "(done_dialog 0)")
     (setq res (start_dialog))
     (unload_dialog id)
     (vl-file-delete dclpath)
     (cond
       ((/= res 1) nil)
       (single
        (setq *VL:PRIV-DIM-CHOICE* (nth i1 names))
        (list *VL:PRIV-DIM-CHOICE* def2))
       (T (setq *VL:DIM-CHOICE* (list (nth i1 names) (nth i2 names))))
     )
    )
    (T
     (princ "\n  Не удалось открыть диалог — использую стили по умолчанию.")
     (list def1 def2)
    )
  )
)


;;; ------------------------------------------------------------
;;; Автоматически подтягивает размерный стиль (DIMSTYLE) из чертежа-
;;; шаблона, если стиля нет в текущем чертеже — тем же способом,
;;; что и стиль мультивыноски: вставка шаблона как временного блока
;;; с последующим удалением.
;;;
;;; Возвращает T, если стиль есть в чертеже, и nil в противном случае.
;;; ------------------------------------------------------------
;;; ------------------------------------------------------------
;;; Принудительно ставит размещение текста "Под линией" (DIMTAD = 4)
;;; для указанного размерного стиля.
;;; ------------------------------------------------------------
(defun vl:force-dimstyle-text-below (style-name / doc styles style old-cmdecho)
  (if (and style-name (vl:dimstyle-exists-p style-name))
    (progn
      (vl-load-com)
      (setq doc    (vla-get-ActiveDocument (vlax-get-acad-object)))
      (setq styles (vla-get-DimStyles doc))
      (setq style  (vl-catch-all-apply 'vla-Item (list styles style-name)))
      (if (not (vl-catch-all-error-p style))
        (progn
          ;; tekst pod liniey
          (vl-catch-all-apply 'vla-SetVariable (list style "DIMTAD" 4))
          ;; ubiraem prefix/suffix stilya, chtoby ne dublrovalos s TextOverride
          (vl-catch-all-apply 'vla-SetVariable (list style "DIMPOST" ""))
          (setq old-cmdecho (getvar "CMDECHO"))
          (setvar "CMDECHO" 0)
          (vl-catch-all-apply
            '(lambda ()
               (command "_.-DIMSTYLE" "_R" style-name)
               (setvar "DIMTAD" 4)
               (setvar "DIMPOST" "")
               (command "_.-DIMSTYLE" "_S" style-name "_Y")
             )
          )
          (setvar "CMDECHO" old-cmdecho)
        )
      )
    )
  )
  style-name
)

(defun vl:ensure-dimstyle-from-template (template-path dim-style
                                          / old-filedia old-cmdecho old-osmode)
  (if (vl:dimstyle-exists-p dim-style)
    T
    (if (not (findfile template-path))
      (progn
        (princ (strcat "\n  ПРЕДУПРЕЖДЕНИЕ: файл шаблона не найден: " template-path))
        nil
      )
      (progn
        (setq old-filedia (getvar "FILEDIA"))
        (setq old-cmdecho (getvar "CMDECHO"))
        (setq old-osmode  (getvar "OSMODE"))
        (setvar "FILEDIA" 0)
        (setvar "CMDECHO" 0)
        (setvar "OSMODE"  0)

        ;; Перед INSERT — если блок с таким именем уже "болтается" в таблице
        ;; блоков (осталось от прошлой вставки шаблона), убираем его,
        ;; чтобы -INSERT не переспрашивал "переопределить?"
        (setq tmpl-block-name (vl-filename-base template-path))
        (if (tblsearch "BLOCK" tmpl-block-name)
          (command "_.-PURGE" "_B" tmpl-block-name "_N")
        )

        (command "_.-INSERT" template-path "_S" 1.0 "0,0,0" 0.0)
        (while (> (getvar "CMDACTIVE") 0) (command ""))
        (command "_.ERASE" "_L" "")
        (while (> (getvar "CMDACTIVE") 0) (command ""))

        (setvar "FILEDIA" old-filedia)
        (setvar "CMDECHO" old-cmdecho)
        (setvar "OSMODE"  old-osmode)

        (if (vl:dimstyle-exists-p dim-style)
          T
          (progn
            (princ (strcat "\n  ПРЕДУПРЕЖДЕНИЕ: импорт не удался, размерный стиль «"
                           dim-style "» не появился в чертеже."))
            nil
          )
        )
      )
    )
  )
)

;;; ------------------------------------------------------------
;;; Проверяет / импортирует атрибутивный блок coord-block-name из
;;; чертежа-шаблона (если его ещё нет в текущем чертеже).
;;; Вызывается ОДИН РАЗ до начала цикла по вершинам — не путать
;;; с вставкой самого блока в вершину (это делает
;;; vl:insert-coord-block отдельно для каждой вершины).
;;;
;;; Возвращает T, если блок в итоге есть в чертеже, иначе nil.
;;; ------------------------------------------------------------
(defun vl:ensure-coord-block-from-template (template-path block-name
                                             / old-filedia)
  (if (tblsearch "BLOCK" block-name)
    T
    (if (not (findfile template-path))
      (progn
        (princ (strcat "\n  ПРЕДУПРЕЖДЕНИЕ: файл шаблона не найден: " template-path))
        nil
      )
      (progn
        (setq old-filedia (getvar "FILEDIA"))
        (setvar "FILEDIA" 0)

        ;; Синтаксис "путь_к_dwg=имя_блока" — INSERT берёт из внешнего
        ;; DWG именно вложенный блок с таким именем, а не весь чертёж.
        (command "_.-INSERT" (strcat block-name "=" template-path) "_S" 1.0 "0,0,0" 0.0)
        ;; Сбрасываем "зависшие" запросы, если -INSERT ждёт ещё ввода
        ;; (например, диалог "Блок уже существует. Переопределить?")
        (while (> (getvar "CMDACTIVE") 0)
          (command "")
        )

        (command "_.ERASE" "_L" "")
        (while (> (getvar "CMDACTIVE") 0)
          (command "")
        )

        (setvar "FILEDIA" old-filedia)

        (if (tblsearch "BLOCK" block-name)
          T
          (progn
            (princ (strcat "\n  ОШИБКА: блок «" block-name
                           "» не найден ни в чертеже, ни в шаблоне."))
            nil
          )
        )
      )
    )
  )
)

;;; ------------------------------------------------------------
;;; Создаёт MLEADER (мультивыноску) через ActiveX (vla-объекты).
;;; Все ключевые параметры назначаются напрямую каждому объекту —
;;; это гарантирует правильный вид независимо от базового стиля.
;;;
;;; Аргументы:
;;;   pt-arrow   — точка «острия» выноски
;;;   pt-land    — точка начала горизонтальной полки
;;;   pt-text    — точка привязки текста (справочно, для геометрии
;;;                самой линии выноски; фактическая длина полки
;;;                задаётся отдельно параметром dogleg-len)
;;;   mtext-str  — строка содержимого
;;;   style-name — имя базового стиля MLEADER
;;;   dogleg-len — желаемая длина горизонтальной полки
;;;
;;; Возвращает: entity name созданного MLEADER или nil
;;; ------------------------------------------------------------
(defun vl:create-mleader (pt-arrow pt-land pt-text mtext-str style-name dogleg-len txt-h
                           / acadobj mspace mleader pts-variant old-cmleaderstyle)
  (vl-load-com)
  (setq acadobj (vlax-get-acad-object))
  (setq mspace  (vla-get-modelspace (vla-get-activedocument acadobj)))

  (setq old-cmleaderstyle (getvar "CMLEADERSTYLE"))
  (if (vl:mleader-style-exists-p style-name)
    (vl-catch-all-apply 'setvar (list "CMLEADERSTYLE" style-name))
  )

  (setq pts-variant
    (vlax-make-safearray vlax-vbdouble '(0 . 5))
  )
  (vlax-safearray-put-element pts-variant 0 (car   pt-arrow))
  (vlax-safearray-put-element pts-variant 1 (cadr  pt-arrow))
  (vlax-safearray-put-element pts-variant 2 (caddr pt-arrow))
  (vlax-safearray-put-element pts-variant 3 (car   pt-land))
  (vlax-safearray-put-element pts-variant 4 (cadr  pt-land))
  (vlax-safearray-put-element pts-variant 5 (caddr pt-land))

  (setq mleader (vla-AddMLeader mspace pts-variant 0))

  (setvar "CMLEADERSTYLE" old-cmleaderstyle)

  (if (null mleader)
    (progn (princ "\n  ОШИБКА: не удалось создать MLEADER.") nil)
    (progn
      (vl-catch-all-apply
        '(lambda () (vla-put-StyleName mleader style-name))
      )
      (vl-catch-all-apply
        '(lambda () (vla-put-ArrowheadType mleader 20))
      )
      (vl-catch-all-apply
        '(lambda () (vla-put-EnableDogleg mleader :vlax-true))
      )
      (vl-catch-all-apply
        '(lambda () (vla-put-DoglegLength mleader dogleg-len))
      )
      (vl-catch-all-apply
        '(lambda () (vla-put-LeaderLineType mleader 1))
      )
      (vl-catch-all-apply
        '(lambda () (vla-put-ContentType mleader 1))
      )
      (vl-catch-all-apply
        '(lambda () (vla-put-TextString mleader mtext-str))
      )
      ;; --- ВАЖНО: принудительно задаём высоту текста ---
      (if txt-h
        (vl-catch-all-apply
          '(lambda () (vla-put-TextHeight mleader (float txt-h)))
        )
      )
      (vl-catch-all-apply
        '(lambda () (vla-put-TextAttachmentType mleader 1))
      )
      (vl-catch-all-apply
        '(lambda () (vla-put-TextAngle mleader 0.0))
      )
      (vl-catch-all-apply
        '(lambda ()
           (vla-put-TextBackgroundFill mleader :vlax-true)
           (vla-put-TextBackgroundScaleFactor mleader 1.05)
           (vla-put-TextBackgroundColor mleader 254)
        )
      )
      (vlax-vla-object->ename mleader)
    )
  )
)

;;; ------------------------------------------------------------
;;; ??????? MTEXT ? ?????????? ?????? ???? ? ???????? ?????????
;;; ??????.
;;;
;;; ?????????:
;;;   ins-pt     — ????? ??????? ??????
;;;   txt-str    — ?????? ??????
;;;   height     — ?????? ??????
;;;   width      — ?????? ?????????? ???? (0 = ????)
;;;   just       — ???????????? (AttachmentPoint)
;;;   style-name — ??? ?????????? ?????
;;; ------------------------------------------------------------

(defun vl:set-mtext-mask-scale (ename scale / elst)
  (setq elst (entget ename '("*")))

  (if (assoc 45 elst)
    (setq elst
          (subst
            (cons 45 (float scale))
            (assoc 45 elst)
            elst))
    (setq elst
          (append elst
                  (list (cons 45 (float scale)))))
  )

  (entmod elst)
  (entupd ename)
  ename
)

;;; ------------------------------------------------------------
;;; Создаёт слой, если его нет. Возвращает имя слоя.
;;; ------------------------------------------------------------
(defun vl:ensure-layer (layer-name aci-color / doc layers lay res)
  (vl-load-com)
  (setq doc    (vla-get-ActiveDocument (vlax-get-acad-object)))
  (setq layers (vla-get-Layers doc))
  (setq res (vl-catch-all-apply 'vla-Item (list layers layer-name)))
  (if (vl-catch-all-error-p res)
    (progn
      (setq lay (vla-Add layers layer-name))
      (vl-catch-all-apply '(lambda () (vla-put-Color lay aci-color)))
    )
  )
  layer-name
)

;;; ------------------------------------------------------------
;;; Создаёт MTEXT с маской фона. Номера вершин: зелёный цвет (3),
;;; слой «вершины координат».
;;; ------------------------------------------------------------
(defun vl:create-mtext-masked
       (ins-pt txt-str height width just style-name
        / doc mspace mt en vert-layer)

  (vl-load-com)

  (setq vert-layer "вершины координат")
  (vl:ensure-layer vert-layer 3)

  (setq doc    (vla-get-ActiveDocument (vlax-get-acad-object)))
  (setq mspace (vla-get-ModelSpace doc))

  (setq mt
        (vla-AddMText
          mspace
          (vlax-3d-point ins-pt)
          (float width)
          txt-str))

  (if mt
    (progn

      ;; Высота
      (vla-put-Height mt (float height))

      ;; Стиль
      (vl-catch-all-apply
        '(lambda ()
           (vla-put-StyleName mt style-name)))

      ;; Выравнивание
      (vla-put-AttachmentPoint mt just)

      ;; Слой и цвет (зелёный = 3)
      (vl-catch-all-apply
        '(lambda ()
           (vla-put-Layer mt vert-layer)))
      (vl-catch-all-apply
        '(lambda ()
           (vla-put-Color mt 3)))

      ;; Маска
      (vl-catch-all-apply
        '(lambda ()
           (vla-put-BackgroundFill mt :vlax-true)
           (vla-put-BackgroundColor mt 254)
         )
      )

      ;; Получаем имя объекта
      (setq en (vlax-vla-object->ename mt))

      ;; Принудительно меняем DXF код 45
      (vl:set-mtext-mask-scale en 1.05)

      en
    )
  )
)


;;; ------------------------------------------------------------
;;; Вставляет блок с атрибутами координат — альтернатива MLEADER.
;;; Блок должен быть атрибутивным, с тегами атрибутов "X" и "Y".
;;; Блок вставляется точкой вставки прямо в вершину полилинии —
;;; никакой дополнительной "выносной" геометрии не создаётся.
;;;
;;; Строки x-str/y-str должны уже содержать знак +/- (см.
;;; vl:fmt-coord) — они попадают в атрибуты как есть, без
;;; дополнительных префиксов "X="/"Y=" (эти префиксы уже
;;; нарисованы статикой внутри самого блока).
;;;
;;; Высота текста атрибутов X/Y принудительно выставляется равной
;;; txt-height — той же высоте, что используется для мультивыносок
;;; и подписей номеров вершин. Это гарантирует одинаковый размер
;;; текста независимо от масштаба, в котором нарисован сам блок.
;;;
;;; Аргументы:
;;;   pt-vertex  — точка вершины полилинии (она же точка вставки блока)
;;;   block-name — имя блока в чертеже (блок должен уже существовать —
;;;                см. vl:ensure-coord-block-from-template)
;;;   x-str,y-str— отформатированные строки координат (со знаком +/-)
;;;   scale      — масштаб вставки блока (геометрия/пропорции блока,
;;;                НЕ высота текста — та задаётся отдельно)
;;;   txt-height — требуемая высота текста атрибутов (как у мультивыноски)
;;;
;;; Возвращает: entity name вставленного блока или nil
;;; ------------------------------------------------------------

;; --- Глобальные переменные для системы реакторов координатных блоков ---

(if (not *VL:COORD-REACTORS*)          (setq *VL:COORD-REACTORS* '()))
(if (not *VL:COORD-BLOCK-NAME*)        (setq *VL:COORD-BLOCK-NAME* nil))
(if (not *VL:COORD-DIRTY*)             (setq *VL:COORD-DIRTY* '()))
(if (not *VL:COORD-CMD-REACTOR*)       (setq *VL:COORD-CMD-REACTOR* nil))
(if (not *VL:COORD-ATTACHED-HANDLES*)  (setq *VL:COORD-ATTACHED-HANDLES* '()))

;; ------------------------------------------------------------
;; Пересчитывает и перезаписывает атрибуты X/Y блока по его
;; ТЕКУЩЕЙ точке вставки (InsertionPoint). Использует тот же
;; формат, что и при первичной вставке (vl:fmt-coord).
;; Вызывать ТОЛЬКО когда безопасно менять объект (после
;; завершения команды, не изнутри :vlr-modified!).
;; ------------------------------------------------------------
(defun vl:refresh-coord-attrs (blk-obj / pt x y atts att tag)
  (setq pt (vl-catch-all-apply 'vlax-get (list blk-obj 'InsertionPoint)))
  (if (not (vl-catch-all-error-p pt))
    (progn
      (setq x (cadr pt))   ; "геодезическая" X = вертикаль чертежа
      (setq y (car pt))    ; "геодезическая" Y = горизонталь чертежа
      (setq atts (vl-catch-all-apply 'vlax-invoke (list blk-obj 'GetAttributes)))
      (if (not (vl-catch-all-error-p atts))
        (foreach att atts
          (setq tag (strcase (vla-get-TagString att)))
          (cond
            ((member tag '("X" "Х")) (vla-put-TextString att (strcat "X= " (vl:fmt-coord x))))
            ((member tag '("Y" "У")) (vla-put-TextString att (strcat "Y= " (vl:fmt-coord y))))
          )
        )
      )
      (vl-catch-all-apply 'vla-Update (list blk-obj))
    )
  )
)

;; ------------------------------------------------------------
;; Callback объектного реактора (:vlr-modified).
;; КРИТИЧЕСКИ ВАЖНО: здесь НЕЛЬЗЯ менять blk-obj (и его атрибуты) —
;; AutoCAD ещё находится в процессе рассылки уведомления, и попытка
;; изменить объект прямо тут вызывает аварийное завершение
;; (dbattr.cpp eWasNotifying). Поэтому только откладываем работу —
;; складываем объект в список "грязных" для последующей обработки.
;; ------------------------------------------------------------
(defun vl:coord-block-modified (notifier-obj reactor-obj param-list / )
  (if (not (member notifier-obj *VL:COORD-DIRTY*))
    (setq *VL:COORD-DIRTY* (cons notifier-obj *VL:COORD-DIRTY*))
  )
)

;; ------------------------------------------------------------
;; Ищет в чертеже все вставки координатного блока, у которых ещё
;; нет реактора (новые копии), навешивает на них реактор и сразу
;; пересчитывает их X/Y по текущему положению.
;; Вызывается после КАЖДОЙ команды (см. vl:coord-cmd-ended) —
;; поэтому копирование блока подхватывается автоматически.
;; ------------------------------------------------------------
(defun vl:auto-attach-new-coord-blocks (/ bname ss i ent obj hnd)
  (setq bname (if *VL:COORD-BLOCK-NAME* *VL:COORD-BLOCK-NAME* nil))
  (if bname
    (progn
      (setq ss (ssget "_X" (list (cons 0 "INSERT") (cons 2 bname))))
      (if ss
        (progn
          (setq i 0)
          (repeat (sslength ss)
            (setq ent (ssname ss i))
            (setq hnd (cdr (assoc 5 (entget ent))))
            (if (and hnd (not (member hnd *VL:COORD-ATTACHED-HANDLES*)))
              (progn
                (setq obj (vlax-ename->vla-object ent))
                ;; (vl:attach-coord-reactor obj)
                ;; (vl-catch-all-apply 'vl:refresh-coord-attrs (list obj))
              )
            )
            (setq i (1+ i))
          )
        )
      )
    )
  )
)

;; ------------------------------------------------------------
;; Callback реактора команд (:vlr-commandEnded / Cancelled / Failed).
;; Срабатывает ПОСЛЕ полного завершения команды — в этот момент
;; уведомления уже закончены, и менять объекты полностью безопасно.
;; Обрабатывает всё накопленное в *VL:COORD-DIRTY* и очищает список.
;; ------------------------------------------------------------
(defun vl:coord-cmd-ended (calling-reactor param-list / obj chk)
  (if *VL:COORD-DIRTY*
    (progn
      (foreach obj *VL:COORD-DIRTY*
        (setq chk (vl-catch-all-apply 'vla-get-ObjectName (list obj)))
        (if (not (vl-catch-all-error-p chk))
          (vl-catch-all-apply 'vl:refresh-coord-attrs (list obj))
        )
      )
      (setq *VL:COORD-DIRTY* '())
    )
  )
  (vl-catch-all-apply 'vl:auto-attach-new-coord-blocks nil)
)

;; --- Регистрирует реактор команд один раз за сеанс AutoCAD ---
(defun vl:ensure-coord-cmd-reactor ()
  (if (not *VL:COORD-CMD-REACTOR*)
    (setq *VL:COORD-CMD-REACTOR*
      (vlr-command-reactor
        nil
        (list
          (cons :vlr-commandEnded     'vl:coord-cmd-ended)
          (cons :vlr-commandCancelled 'vl:coord-cmd-ended)
          (cons :vlr-commandFailed    'vl:coord-cmd-ended)
        )
      )
    )
  )
)

;; --- Навешивает объектный реактор на один блок ---
(defun vl:attach-coord-reactor (blk-obj / hnd)
  (vl:ensure-coord-cmd-reactor)
  (setq hnd (vl-catch-all-apply 'vla-get-Handle (list blk-obj)))
  (if (not (vl-catch-all-error-p hnd))
    (setq *VL:COORD-ATTACHED-HANDLES* (cons hnd *VL:COORD-ATTACHED-HANDLES*))
  )
  (setq *VL:COORD-REACTORS*
    (cons
      (vlr-object-reactor (list blk-obj) nil (list (cons :vlr-modified 'vl:coord-block-modified)))
      *VL:COORD-REACTORS*
    )
  )
)

;; ------------------------------------------------------------
;; Команда: пере-навешивает реакторы на ВСЕ координатные блоки
;; в чертеже. Реакторы НЕ сохраняются в DWG между сеансами —
;; запускайте эту команду один раз после каждого открытия файла.
;; ------------------------------------------------------------
(defun c:REFRESHCOORDBLOCKS ( / ss i ent obj bname)
  (vl-load-com)
  (vl:ensure-coord-cmd-reactor)
  (setq bname (if *VL:COORD-BLOCK-NAME* *VL:COORD-BLOCK-NAME* "XY"))
  (setq *VL:COORD-REACTORS* '())
  (setq *VL:COORD-DIRTY* '())
  (setq *VL:COORD-ATTACHED-HANDLES* '())
  (setq ss (ssget "X" (list (cons 0 "INSERT") (cons 2 bname))))
  (setq i 0)
  (if ss
    (repeat (sslength ss)
      (setq ent (ssname ss i))
      (setq obj (vlax-ename->vla-object ent))
      ;; (vl:attach-coord-reactor obj)
      (setq i (1+ i))
    )
  )
  (princ (strcat "\n  Реакторы навешены на " (itoa i) " блок(ов) «" bname "»."))
  (princ)
)

;;; ============================================================
;;; АВТОРАССТАНОВКА ПОДПИСЕЙ БЕЗ ПЕРЕСЕЧЕНИЙ
;;; ============================================================

(if (not (boundp '*VL:PLACED-BBOXES*)) (setq *VL:PLACED-BBOXES* '()))

(defun vl:estimate-text-width (txt-str height / n)
  (setq n (strlen txt-str))
  (* n height 0.75)   ; чуть шире — запас под реальный шрифт
)

(defun vl:bbox-make-centered (cx cy w h)
  (list
    (- cx (/ w 2.0))   ; min X
    (- cy (/ h 2.0))   ; min Y
    (+ cx (/ w 2.0))   ; max X
    (+ cy (/ h 2.0))   ; max Y
  )
)

(defun vl:bbox-overlap-p (b1 b2)
  (not (or (< (nth 2 b1) (nth 0 b2))
           (< (nth 2 b2) (nth 0 b1))
           (< (nth 3 b1) (nth 1 b2))
           (< (nth 3 b2) (nth 1 b1))
      )
  )
)

(defun vl:pt-in-bbox-p (pt bbox)
  (and (>= (car pt)  (nth 0 bbox)) (<= (car pt)  (nth 2 bbox))
       (>= (cadr pt) (nth 1 bbox)) (<= (cadr pt) (nth 3 bbox)))
)

(defun vl:cross2d (ox oy ax ay bx by)
  (- (* (- ax ox) (- by oy)) (* (- ay oy) (- bx ox)))
)

(defun vl:seg-seg-intersect-p (p1 p2 p3 p4 / d1 d2 d3 d4)
  (setq d1 (vl:cross2d (car p3) (cadr p3) (car p4) (cadr p4) (car p1) (cadr p1)))
  (setq d2 (vl:cross2d (car p3) (cadr p3) (car p4) (cadr p4) (car p2) (cadr p2)))
  (setq d3 (vl:cross2d (car p1) (cadr p1) (car p2) (cadr p2) (car p3) (cadr p3)))
  (setq d4 (vl:cross2d (car p1) (cadr p1) (car p2) (cadr p2) (car p4) (cadr p4)))
  (and
    (or (and (> d1 0) (< d2 0)) (and (< d1 0) (> d2 0)))
    (or (and (> d3 0) (< d4 0)) (and (< d3 0) (> d4 0)))
  )
)

(defun vl:bbox-seg-intersect-p (bbox p1 p2 / minx miny maxx maxy)
  (setq minx (nth 0 bbox) miny (nth 1 bbox) maxx (nth 2 bbox) maxy (nth 3 bbox))
  (or
    (vl:pt-in-bbox-p p1 bbox)
    (vl:pt-in-bbox-p p2 bbox)
    (vl:seg-seg-intersect-p p1 p2 (list minx miny) (list maxx miny))
    (vl:seg-seg-intersect-p p1 p2 (list maxx miny) (list maxx maxy))
    (vl:seg-seg-intersect-p p1 p2 (list maxx maxy) (list minx maxy))
    (vl:seg-seg-intersect-p p1 p2 (list minx maxy) (list minx miny))
  )
)

;; Тот же тест, что и vl:bbox-seg-intersect-p, но БЕЗ проверки
;; "конец отрезка внутри бокса" — только реальное пересечение линии
;; сегмента с гранями бокса. Нужен для двух сегментов, примыкающих
;; к текущей вершине: то, что сама вершина рядом с боксом подписи —
;; это не пересечение, а вот если линия сегмента проходит сквозь
;; бокс — это реальное наложение, и его пропускать нельзя.
(defun vl:bbox-seg-intersect-line-only-p (bbox p1 p2 / minx miny maxx maxy)
  (setq minx (nth 0 bbox) miny (nth 1 bbox) maxx (nth 2 bbox) maxy (nth 3 bbox))
  (or
    (vl:seg-seg-intersect-p p1 p2 (list minx miny) (list maxx miny))
    (vl:seg-seg-intersect-p p1 p2 (list maxx miny) (list maxx maxy))
    (vl:seg-seg-intersect-p p1 p2 (list maxx maxy) (list minx maxy))
    (vl:seg-seg-intersect-p p1 p2 (list minx maxy) (list minx miny))
  )
)

(defun vl:candidate-point (base-pt angle-deg radius / rad)
  (setq rad (* angle-deg (/ pi 180.0)))
  (list (+ (car base-pt)  (* radius (cos rad)))
        (+ (cadr base-pt) (* radius (sin rad)))
        0.0)
)

;; Если после теста подписи начнут уходить НЕ наружу от контура,
;; а внутрь фигуры — поменяйте 1.0 на -1.0 в этой строке.
(if (not (boundp '*VL:OUTWARD-DIR-FLIP*)) (setq *VL:OUTWARD-DIR-FLIP* 1.0))

;; Знак ориентации обхода полилинии по формуле площади (шнуровка):
;; >0 — против часовой стрелки, <0 — по часовой стрелке.
;; Для разомкнутой полилинии однозначного "наружу" не существует —
;; возвращаем 1.0, направление всё равно будет консистентным.
(defun vl:polygon-orientation-sign (vertices seg-count closed / area i n p1 p2)
  (setq area 0.0)
  (if closed
    (progn
      (setq n (1+ seg-count))
      (setq i 0)
      (repeat n
        (setq p1 (nth i vertices))
        (setq p2 (nth (rem (1+ i) n) vertices))
        (setq area (+ area (- (* (car p1) (cadr p2)) (* (car p2) (cadr p1)))))
        (setq i (1+ i))
      )
    )
  )
  (* (if (>= area 0.0) 1.0 -1.0) *VL:OUTWARD-DIR-FLIP*)
)

;; Направление "наружу" от контура в данной вершине, в градусах
;; (0 = вправо, 90 = вверх, стандартная математическая система углов,
;; та же, что использует vl:candidate-point).
(defun vl:outward-angle (vertices seg-count vertex-idx closed sign
                          / prev-pt next-pt v1 nx1 ny1 nx2 ny2 nx ny len)
  (setq prev-pt nil next-pt nil)
  (if (or closed (> vertex-idx 0))
    (setq prev-pt (nth (if (= vertex-idx 0) seg-count (1- vertex-idx)) vertices))
  )
  (if (or closed (< vertex-idx seg-count))
    (setq next-pt (nth (if (= vertex-idx seg-count) 0 (1+ vertex-idx)) vertices))
  )
  (setq v1 (nth vertex-idx vertices))

  (cond
    ((and prev-pt next-pt)
     (setq nx1 (* sign (- (cadr v1) (cadr prev-pt))))
     (setq ny1 (* sign (- (car prev-pt) (car v1))))
     (setq nx2 (* sign (- (cadr next-pt) (cadr v1))))
     (setq ny2 (* sign (- (car v1) (car next-pt))))
     (setq nx (+ nx1 nx2))
     (setq ny (+ ny1 ny2))
    )
    (next-pt
     (setq nx (* sign (- (cadr next-pt) (cadr v1))))
     (setq ny (* sign (- (car v1) (car next-pt))))
    )
    (prev-pt
     (setq nx (* sign (- (cadr v1) (cadr prev-pt))))
     (setq ny (* sign (- (car prev-pt) (car v1))))
    )
    (T (setq nx 1.0 ny 0.0))
  )

  (setq len (sqrt (+ (* nx nx) (* ny ny))))
  (if (< len 1e-9)
    0.0
    (* (/ (atan ny nx) pi) 180.0)
  )
)

;; Пересортировывает список angles по возрастанию углового расстояния
;; до target-angle — первым идёт направление, ближе всего к "наружу".
(defun vl:sort-angles-by-target (angles target-angle / lst a diff)
  (setq lst '())
  (foreach a angles
    (setq diff (- a target-angle))
    (setq diff (- diff (* 360.0 (fix (/ diff 360.0)))))
    (if (> diff 180.0) (setq diff (- diff 360.0)))
    (if (< diff -180.0) (setq diff (+ diff 360.0)))
    (setq lst (cons (list (abs diff) a) lst))
  )
  (setq lst (vl-sort lst '(lambda (x y) (< (car x) (car y)))))
  (mapcar 'cadr lst)
)


;;; ------------------------------------------------------------
;;; Сетка ячеек для подписей и сегментов.
;;; Ключ ячейки — (ix . iy), в ячейке список объектов.
;;; Проверка кандидата смотрит только соседние ячейки и
;;; прекращается на первом пересечении.
;;; ------------------------------------------------------------
(if (not (boundp '*VL:GRID-CELL*)) (setq *VL:GRID-CELL* 30.0))
(if (not (boundp '*VL:LABEL-GRID*)) (setq *VL:LABEL-GRID* nil))
(if (not (boundp '*VL:SEG-GRID*)) (setq *VL:SEG-GRID* nil))
(if (not (boundp '*VL:SEG-GRID-SRC*)) (setq *VL:SEG-GRID-SRC* nil))
(if (not (boundp '*VL:SEG-GRID-CLOSED*)) (setq *VL:SEG-GRID-CLOSED* nil))
(if (not (boundp '*VL:SEG-GRID-COUNT*)) (setq *VL:SEG-GRID-COUNT* nil))
(if (not (boundp '*VL:ORIENT-SIGN*)) (setq *VL:ORIENT-SIGN* 1.0))

(defun vl:reset-placement-index ()
  (setq *VL:PLACED-BBOXES* '())
  (setq *VL:LABEL-GRID* nil)
  (setq *VL:SEG-GRID* nil)
  (setq *VL:SEG-GRID-SRC* nil)
  (setq *VL:SEG-GRID-CLOSED* nil)
  (setq *VL:SEG-GRID-COUNT* nil)
)

(defun vl:grid-add (grid item minx miny maxx maxy cell / ix ix1 iy iy0 iy1 key old)
  (setq ix  (fix (/ minx cell))
        ix1 (fix (/ maxx cell))
        iy0 (fix (/ miny cell))
        iy1 (fix (/ maxy cell)))
  (while (<= ix ix1)
    (setq iy iy0)
    (while (<= iy iy1)
      (setq key (cons ix iy))
      (setq old (assoc key grid))
      (if old
        (setq grid (subst (cons key (cons item (cdr old))) old grid))
        (setq grid (cons (cons key (list item)) grid))
      )
      (setq iy (1+ iy))
    )
    (setq ix (1+ ix))
  )
  grid
)

(defun vl:grid-query (grid minx miny maxx maxy cell / ix ix1 iy iy0 iy1 row acc b)
  (setq acc nil
        ix  (fix (/ minx cell))
        ix1 (fix (/ maxx cell))
        iy0 (fix (/ miny cell))
        iy1 (fix (/ maxy cell)))
  (while (<= ix ix1)
    (setq iy iy0)
    (while (<= iy iy1)
      (setq row (cdr (assoc (cons ix iy) grid)))
      (foreach b row
        (if (not (member b acc))
          (setq acc (cons b acc))
        )
      )
      (setq iy (1+ iy))
    )
    (setq ix (1+ ix))
  )
  acc
)

(defun vl:grid-add-bbox (grid bbox cell)
  (vl:grid-add grid bbox (nth 0 bbox) (nth 1 bbox) (nth 2 bbox) (nth 3 bbox) cell)
)

(defun vl:grid-add-seg (grid rec cell / p1 p2 minx maxx miny maxy)
  (setq p1 (cadr rec) p2 (caddr rec))
  (setq minx (min (car p1) (car p2))
        maxx (max (car p1) (car p2))
        miny (min (cadr p1) (cadr p2))
        maxy (max (cadr p1) (cadr p2)))
  (vl:grid-add grid rec minx miny maxx maxy cell)
)

(defun vl:build-seg-grid (vertices seg-count closed cell / grid i rest p1 p2)
  (setq grid nil i 0 rest vertices)
  (repeat seg-count
    (setq p1 (car rest)
          p2 (cadr rest)
          rest (cdr rest))
    (if (and p1 p2)
      (setq grid (vl:grid-add-seg grid (list i p1 p2 nil) cell))
    )
    (setq i (1+ i))
  )
  (if (and closed (car vertices) (nth seg-count vertices))
    (setq grid
      (vl:grid-add-seg grid
        (list seg-count (nth seg-count vertices) (car vertices) T)
        cell))
  )
  grid
)

(defun vl:ensure-seg-grid (vertices seg-count closed / )
  (if (not (and (eq *VL:SEG-GRID-SRC* vertices)
                (eq *VL:SEG-GRID-CLOSED* closed)
                (= *VL:SEG-GRID-COUNT* seg-count)))
    (progn
      (setq *VL:SEG-GRID* (vl:build-seg-grid vertices seg-count closed *VL:GRID-CELL*))
      (setq *VL:SEG-GRID-SRC* vertices)
      (setq *VL:SEG-GRID-CLOSED* closed)
      (setq *VL:SEG-GRID-COUNT* seg-count)
      (setq *VL:ORIENT-SIGN* (vl:polygon-orientation-sign vertices seg-count closed))
    )
  )
  *VL:SEG-GRID*
)

(defun vl:find-label-placement (vertex-pt label-w label-h vertices seg-count base-radius vertex-idx closed
                                 / angles radii found best-pt cand cbbox ok
                                   outward-ang sorted-angles
                                   pad dogleg text-left text-right text-bot text-top
                                   rad ang ri rn ai an hits rec seg-i p1 p2 cell)

  ;; Текст ставится справа от точки приземления на длину dogleg.
  ;; Кандидаты идут от направления «наружу». Первый свободный — результат.
  (setq dogleg base-radius)
  (setq pad (* label-h 0.35))
  (setq cell *VL:GRID-CELL*)
  (if (or (null cell) (<= cell 1e-6)) (setq cell 30.0))

  (vl:ensure-seg-grid vertices seg-count closed)
  (setq outward-ang
    (vl:outward-angle vertices seg-count vertex-idx closed *VL:ORIENT-SIGN*))
  (if (null outward-ang) (setq outward-ang 0.0))

  (setq angles '(0 15 30 45 60 75 90 105 120 135 150 165 180
                 195 210 225 240 255 270 285 300 315 330 345))
  (setq sorted-angles (vl:sort-angles-by-target angles outward-ang))

  (setq radii (list (* base-radius 3.0)
                    (* base-radius 5.0)
                    (* base-radius 7.5)
                    (* base-radius 11.0)
                    (* base-radius 16.0)
                    (* base-radius 22.0)
                    (* base-radius 30.0)))

  (setq found nil
        ri 0
        rn (length radii)
        an (length sorted-angles))

  (while (and (not found) (< ri rn))
    (setq rad (nth ri radii)
          ai 0)
    (while (and (not found) (< ai an))
      (setq ang (nth ai sorted-angles))
      (setq cand (vl:candidate-point vertex-pt ang rad))

      (setq text-left  (+ (car cand) dogleg))
      (setq text-right (+ text-left label-w))
      (setq text-bot   (- (cadr cand) (/ label-h 2.0)))
      (setq text-top   (+ (cadr cand) (/ label-h 2.0)))
      (setq cbbox (list (- text-left pad)
                        (- text-bot pad)
                        (+ text-right pad)
                        (+ text-top pad)))

      (setq ok T)

      ;; уже поставленные подписи — только ячейки этого бокса
      (setq hits (vl:grid-query *VL:LABEL-GRID*
                   (nth 0 cbbox) (nth 1 cbbox) (nth 2 cbbox) (nth 3 cbbox) cell))
      (while (and ok hits)
        (if (vl:bbox-overlap-p cbbox (car hits))
          (setq ok nil)
        )
        (setq hits (cdr hits))
      )

      ;; сегменты полилинии — только ячейки этого бокса
      (if ok
        (setq hits (vl:grid-query *VL:SEG-GRID*
                     (nth 0 cbbox) (nth 1 cbbox) (nth 2 cbbox) (nth 3 cbbox) cell))
      )
      (while (and ok hits)
        (setq rec (car hits)
              hits (cdr hits)
              seg-i (car rec)
              p1 (cadr rec)
              p2 (caddr rec))
        (if (or (= seg-i (1- vertex-idx))
                (= seg-i vertex-idx)
                (and (cadddr rec)
                     (or (= vertex-idx 0) (= vertex-idx seg-count))))
          (if (vl:bbox-seg-intersect-line-only-p cbbox p1 p2) (setq ok nil))
          (if (vl:bbox-seg-intersect-p cbbox p1 p2) (setq ok nil))
        )
      )

      (if ok
        (progn
          (setq best-pt cand)
          (setq found T)
        )
      )
      (setq ai (1+ ai))
    )
    (setq ri (1+ ri))
  )

  (if (not found)
    (setq best-pt (vl:candidate-point vertex-pt
                    (if outward-ang outward-ang 0.0)
                    (* base-radius 25.0)))
  )

  (setq text-left  (+ (car best-pt) dogleg))
  (setq text-right (+ text-left label-w))
  (setq text-bot   (- (cadr best-pt) (/ label-h 2.0)))
  (setq text-top   (+ (cadr best-pt) (/ label-h 2.0)))
  (setq cbbox (list (- text-left pad)
                    (- text-bot pad)
                    (+ text-right pad)
                    (+ text-top pad)))

  (setq *VL:PLACED-BBOXES* (cons cbbox *VL:PLACED-BBOXES*))
  (setq *VL:LABEL-GRID* (vl:grid-add-bbox *VL:LABEL-GRID* cbbox cell))

  best-pt
)

(if (not (boundp '*VL:COORD-MASTER-ENAME*)) (setq *VL:COORD-MASTER-ENAME* nil))
(if (not (boundp '*VL:COORD-MASTER-PT*))    (setq *VL:COORD-MASTER-PT* nil))

(defun vl:insert-coord-block (pt-vertex block-name x-str y-str scale txt-height rot-ang
                               / acadobj mspace blk-ref atts att tag
                                 props prop pname old-attreq old-attdia old-cmdecho old-osmode
                                 master-valid entget-result)
  (vl-load-com)
  (setq acadobj (vlax-get-acad-object))
  (setq mspace  (vla-get-modelspace (vla-get-activedocument acadobj)))

  (setq old-attreq  (getvar "ATTREQ"))
  (setq old-attdia  (getvar "ATTDIA"))
  (setq old-cmdecho (getvar "CMDECHO"))
  (setq old-osmode  (getvar "OSMODE"))
  (setvar "ATTREQ"  0)
  (setvar "ATTDIA"  0)
  (setvar "CMDECHO" 0)
  (setvar "OSMODE"  0)

  (setq entget-result
    (if *VL:COORD-MASTER-ENAME*
      (vl-catch-all-apply 'entget (list *VL:COORD-MASTER-ENAME*))
      nil
    )
  )
  (setq master-valid
    (and *VL:COORD-MASTER-ENAME*
         (not (vl-catch-all-error-p entget-result))
         entget-result
    )
  )

  (if master-valid
    ;; --- Копируем уже РАБОТАЮЩИЙ экземпляр (одиночное копирование,
    ;; завершается само после второй точки — лишний "" не нужен) ---
    (progn
      (command "_.COPY" *VL:COORD-MASTER-ENAME* ""
               *VL:COORD-MASTER-PT*
               pt-vertex)
      (while (> (getvar "CMDACTIVE") 0) (command ""))
      (setq blk-ref (vl-catch-all-apply 'vlax-ename->vla-object (list (entlast))))
    )
    ;; --- Самый первый экземпляр — создаём командой INSERT ---
    (progn
      (command "_.-INSERT" block-name pt-vertex scale scale rot-ang)
      (while (> (getvar "CMDACTIVE") 0) (command ""))
      (setq blk-ref (vl-catch-all-apply 'vlax-ename->vla-object (list (entlast))))
      (if (not (vl-catch-all-error-p blk-ref))
        (progn
          (setq *VL:COORD-MASTER-ENAME* (vlax-vla-object->ename blk-ref))
          (setq *VL:COORD-MASTER-PT*    pt-vertex)
        )
      )
    )
  )

  (setvar "ATTREQ"  old-attreq)
  (setvar "ATTDIA"  old-attdia)
  (setvar "CMDECHO" old-cmdecho)
  (setvar "OSMODE"  old-osmode)

  (if (or (vl-catch-all-error-p blk-ref) (null blk-ref))
    (progn
      (princ (strcat "\n  ОШИБКА: не удалось создать/скопировать блок «" block-name "»."))
      nil
    )
    (progn
      (vl-catch-all-apply '(lambda () (vla-put-XScaleFactor blk-ref scale)))
      (vl-catch-all-apply '(lambda () (vla-put-YScaleFactor blk-ref scale)))
      (vl-catch-all-apply '(lambda () (vla-put-ZScaleFactor blk-ref scale)))
      (vl-catch-all-apply '(lambda () (vla-put-Rotation blk-ref rot-ang)))

      (setq atts (vl-catch-all-apply 'vlax-invoke (list blk-ref 'GetAttributes)))
      (if (vl-catch-all-error-p atts) (setq atts nil))

      (if (and atts (> (length atts) 0))
        (progn
          (foreach att atts
            (setq tag (strcase (vla-get-TagString att)))
            (if (not (member tag '("X" "Х" "Y" "У")))
              (princ (strcat "\n    [диагностика] тег «" tag "» не распознан."))
            )
            (if (> scale 1e-9)
              (vl-catch-all-apply
                '(lambda () (vla-put-Height att (/ txt-height scale)))
              )
            )
            (vl-catch-all-apply '(lambda () (vla-put-Rotation att 0.0)))
          )
          (vla-Update blk-ref)

          (setq props
            (vl-catch-all-apply 'vlax-invoke (list blk-ref 'GetDynamicBlockProperties))
          )
          (if (not (vl-catch-all-error-p props))
            (foreach prop props
              (setq pname (vla-get-PropertyName prop))
              (if (or (= pname "Расстояние1")
                      (= pname "Distance1")
                      (wcmatch pname "*асстояние*")
                      (wcmatch pname "*istance*"))
                (vl-catch-all-apply '(lambda () (vla-put-Value prop 6.7ф)))
              )
            )
          )
         (vla-Update blk-ref)

          (setq *VL:COORD-BLOCK-NAME* block-name)
        )
        (princ (strcat "\n  ПРЕДУПРЕЖДЕНИЕ: нет атрибутов у блока «" block-name "»."))
      )

      ;; --- Выносим блок на передний план (поверх штриховок/подложки) ---
      (command "_.DRAWORDER" (vlax-vla-object->ename blk-ref) "" "_Front")
      (while (> (getvar "CMDACTIVE") 0) (command ""))



      (vlax-vla-object->ename blk-ref)
    )
  )
)
;;; ------------------------------------------------------------
;;; Всем объектам, созданным после last0, назначает слой и цвет
;;; полилинии poly-ename.
;;; ------------------------------------------------------------
(defun vl:apply-poly-props (last0 poly-ename / poly-obj lay tc e obj)
  (vl-load-com)
  (setq poly-obj (vlax-ename->vla-object poly-ename))
  (setq lay (vla-get-Layer poly-obj))
  (setq tc  (vl-catch-all-apply 'vla-get-TrueColor (list poly-obj)))
  (setq e (if last0 (entnext last0) (entnext)))
  (while e
    (setq obj (vl-catch-all-apply 'vlax-ename->vla-object (list e)))
    (if (not (vl-catch-all-error-p obj))
      (progn
        (vl-catch-all-apply 'vla-put-Layer (list obj lay))
        (if (not (vl-catch-all-error-p tc))
          (vl-catch-all-apply 'vla-put-TrueColor (list obj tc))
        )
      )
    )
    (setq e (entnext e))
  )
  (princ)
)


;;; ------------------------------------------------------------
;;; Точки вершин, где УЖЕ стоит координатная метка: вершины линий
;;; мультивыносок и точки вставки блока block-name (в модели).
;;; Возвращает список (x y).
;;; ------------------------------------------------------------
(defun vl:collect-existing-coord-pts (block-name / res ss i ed g inlead p obj en)
  (setq res '())

  ;; --- Мультивыноски: точки линий выноски из DXF-данных (LEADER_LINE) ---
  (if (setq ss (ssget "_X" '((0 . "MULTILEADER") (410 . "Model"))))
    (progn
      (setq i 0)
      (while (< i (sslength ss))
        (setq ed (entget (ssname ss i)))
        (setq inlead nil)
        (foreach g ed
          (cond
            ((and (= (car g) 304) (= (cdr g) "LEADER_LINE{"))
             (setq inlead T))
            ((and (= (car g) 305) (= (cdr g) "}"))
             (setq inlead nil))
            ((and inlead (= (car g) 10))
             (setq res (cons (list (cadr g) (caddr g)) res)))
          )
        )
        (setq i (1+ i))
      )
    )
  )

  ;; --- Блоки координат ---
  ;; динамический блок после изменения свойств превращается в *U..,
  ;; поэтому сверяем действительное имя (EffectiveName)
  (if (setq ss (ssget "_X" (list '(0 . "INSERT") '(410 . "Model")
                                 (cons 2 (strcat block-name ",`*U*")))))
    (progn
      (setq i 0)
      (while (< i (sslength ss))
        (setq obj (vlax-ename->vla-object (ssname ss i)))
        (setq en  (vl-catch-all-apply 'vla-get-EffectiveName (list obj)))
        (if (and (= (type en) 'STR)
                 (= (strcase en) (strcase block-name)))
          (progn
            (setq p (cdr (assoc 10 (entget (ssname ss i)))))
            (setq res (cons (list (car p) (cadr p)) res))
          )
        )
        (setq i (1+ i))
      )
    )
  )
  res
)

;;; T, если точка pt (по X и Y) совпадает с одной из точек списка.
(defun vl:pt-in-list-p (pt lst tol / found)
  (setq found nil)
  (while (and lst (not found))
    (if (and (< (abs (- (car pt) (car (car lst)))) tol)
             (< (abs (- (cadr pt) (cadr (car lst)))) tol))
      (setq found T)
    )
    (setq lst (cdr lst))
  )
  found
)

;;; ------------------------------------------------------------
;;; Извлекает список вершин из полилинии (LWPOLYLINE или
;;; 2D/3D POLYLINE). Возвращает список точек в формате (x y z).
;;; ------------------------------------------------------------
(defun vl:get-polyline-vertices (ename / etype vlist vertex-pt)
  (setq etype (cdr (assoc 0 (entget ename))))
  (cond
    ((= etype "LWPOLYLINE")
     (setq vlist '())
     (foreach pair (entget ename)
       (if (= (car pair) 10)
         (setq vlist (append vlist (list (list (cadr pair) (caddr pair) 0.0))))
       )
     )
     vlist
    )
    ((or (= etype "POLYLINE") (= etype "3DPOLYLINE"))
     (setq vlist '())
     (setq vertex-pt (entnext ename))
     (while (and vertex-pt
                 (= (cdr (assoc 0 (entget vertex-pt))) "VERTEX"))
       (setq vlist
         (append vlist (list (cdr (assoc 10 (entget vertex-pt)))))
       )
       (setq vertex-pt (entnext vertex-pt))
     )
     vlist
    )
    (T
     (princ (strcat "\n  ОШИБКА: объект не является полилинией (тип: " etype ")."))
     nil
    )
  )
)

;;; ------------------------------------------------------------
;;; Возвращает высоту текста из системной переменной TEXTSIZE.
;;; Если равна 0 — возвращает разумный дефолт 2.5.
;;; ------------------------------------------------------------
(defun vl:get-text-height (/ h)
  (setq h (getvar "TEXTSIZE"))
  (if (or (null h) (<= h 0.0))
    2.5
    h
  )
)

;;; ------------------------------------------------------------
;;; Экспортирует таблицу координат в CSV-файл (открывается в Excel).
;;; Разделитель ";" — корректно распознаётся Excel с русской локалью.
;;;
;;; Аргумент data-list — список записей вида (idx x-str y-str)
;;; ------------------------------------------------------------
(defun vl:export-csv (data-list csv-path / f row)
  (setq f (open csv-path "w"))
  (if (null f)
    (progn
      (princ (strcat "\n  ОШИБКА: не удалось создать файл " csv-path))
      nil
    )
    (progn
      (write-line "№;X;Y" f)
      (foreach row data-list
        (write-line
          (strcat (itoa (car row)) ";" (cadr row) ";" (caddr row))
          f
        )
      )
      (close f)
      (princ (strcat "\n  Файл CSV сохранён: " csv-path))
      T
    )
  )
)

;;; ------------------------------------------------------------
;;; Экспортирует таблицу координат в RTF-файл с настоящей таблицей
;;; (открывается в Word без COM-автоматизации).
;;;
;;; Аргумент data-list — список записей вида (idx x-str y-str)
;;; ------------------------------------------------------------
(defun vl:export-rtf (data-list rtf-path / f row col1 col2 col3 row-def)
  (setq f (open rtf-path "w"))
  (if (null f)
    (progn
      (princ (strcat "\n  ОШИБКА: не удалось создать файл " rtf-path))
      nil
    )
    (progn
      (setq col1 1200)
      (setq col2 3600)
      (setq col3 6000)

      (setq row-def
        (strcat
          "\\trowd\\trgaph108\\trleft0"
          "\\clbrdrt\\brdrs\\brdrw10\\clbrdrl\\brdrs\\brdrw10"
          "\\clbrdrb\\brdrs\\brdrw10\\clbrdrr\\brdrs\\brdrw10\\cellx" (itoa col1)
          "\\clbrdrt\\brdrs\\brdrw10\\clbrdrl\\brdrs\\brdrw10"
          "\\clbrdrb\\brdrs\\brdrw10\\clbrdrr\\brdrs\\brdrw10\\cellx" (itoa col2)
          "\\clbrdrt\\brdrs\\brdrw10\\clbrdrl\\brdrs\\brdrw10"
          "\\clbrdrb\\brdrs\\brdrw10\\clbrdrr\\brdrs\\brdrw10\\cellx" (itoa col3)
        )
      )

      (write-line "{\\rtf1\\ansi\\ansicpg1251\\deff0" f)
      (write-line "{\\fonttbl{\\f0 Arial;}}" f)
      (write-line "\\f0\\fs24" f)
      (write-line "{\\b Таблица координат вершин полилинии}\\par\\par" f)

      (write-line row-def f)
      (write-line "\\intbl\\qc\\b №\\cell\\qc X\\cell\\qc Y\\cell\\row\\b0" f)

      (foreach row data-list
        (write-line row-def f)
        (write-line
          (strcat
            "\\intbl\\qc " (itoa (car row)) "\\cell"
            "\\qc " (cadr row) "\\cell"
            "\\qc " (caddr row) "\\cell\\row"
          )
          f
        )
      )

      (write-line "}" f)
      (close f)
      (princ (strcat "\n  Файл RTF (Word) сохранён: " rtf-path))
      T
    )
  )
)

;;; ------------------------------------------------------------
;;; Запрашивает у пользователя, нужно ли экспортировать таблицу
;;; координат, и в каком формате (Excel / Word / Оба / Нет).
;;;
;;; Аргумент data-list — список записей вида (idx x-str y-str)
;;; ------------------------------------------------------------
(defun vl:offer-export (data-list / choice base-path)
  (initget "Excel Word Оба Нет")
  (setq choice
    (getkword
      "\nЭкспортировать таблицу координат? [Excel/Word/Оба/Нет] <Нет>: "
    )
  )
  (if (null choice) (setq choice "Нет"))

  (cond
    ((= choice "Нет")
     (princ "\n  Экспорт пропущен.")
    )
    (T
     (setq base-path
       (getfiled "Укажите имя файла для экспорта" "координаты" "csv" 1)
     )
     (if (null base-path)
       (princ "\n  Экспорт отменён пользователем.")
       (progn
         (if (wcmatch (strcase base-path) "*.CSV")
           (setq base-path (substr base-path 1 (- (strlen base-path) 4)))
         )
         (cond
           ((= choice "Excel")
            (vl:export-csv data-list (strcat base-path ".csv"))
           )
           ((= choice "Word")
            (vl:export-rtf data-list (strcat base-path ".rtf"))
           )
           ((= choice "Оба")
            (vl:export-csv data-list (strcat base-path ".csv"))
            (vl:export-rtf data-list (strcat base-path ".rtf"))
           )
         )
       )
     )
    )
  )
)

;;; ------------------------------------------------------------
;;; Задаёт масштаб маски фона мультивыноски (DXF 141) —
;;; маска только у текста. Должна быть определена ДО
;;; vl:create-parallel-dim-with-label.
;;; ------------------------------------------------------------
(defun vl:set-mleader-mask-scale (ename scale / elst new)
  (if ename
    (progn
      (setq elst (entget ename '("*")))
      (if (assoc 141 elst)
        (progn
          (setq new (subst (cons 141 (float scale)) (assoc 141 elst) elst))
          (vl-catch-all-apply 'entmod (list new))
          (entupd ename)
        )
      )
    )
  )
  ename
)

;;; ------------------------------------------------------------
;;; Создаёт параллельный (aligned) размер между двумя точками
;;; с подписью — фактической длиной отрезка (vl:fmt-length).
;;; Длинный сегмент: подпись на размерной линии (<>).
;;; Короткий сегмент: подпись выноской с маской фона 1.05
;;; (маска только у текста).
;;;
;;; Возвращает: entity name размера / мультивыноски, либо nil.
;;; ------------------------------------------------------------
(defun vl:create-parallel-dim-with-label
       (pt1 pt2 offset-dist txt-height dim-style-name mleader-style-name dim-text-gap
        other-verts-list parallel-search-dist
        / acadobj mspace dx dy seg-len perp-x perp-y dim-pt mid-pt
          near-pt to-near-x to-near-y side-dot
          dim-obj length-str char-count required-width label-ename)

  (vl-load-com)
  (setq acadobj (vlax-get-acad-object))
  (setq mspace  (vla-get-modelspace (vla-get-activedocument acadobj)))

  ;; --- Вектор сегмента и его длина ---
  (setq dx (- (car pt2) (car pt1)))
  (setq dy (- (cadr pt2) (cadr pt1)))
  (setq seg-len (sqrt (+ (* dx dx) (* dy dy))))

  (if (< seg-len 1e-9)
    nil
    (progn
      ;; --- Перпендикуляр к сегменту ---
      (setq perp-x (/ (- dy) seg-len)
            perp-y (/ dx seg-len))

      (setq mid-pt
        (list (/ (+ (car pt1) (car pt2)) 2.0)
              (/ (+ (cadr pt1) (cadr pt2)) 2.0)
              0.0)
      )

      ;; --- Выбор стороны размера ---
      (setq near-pt
        (vl:nearest-pt-on-verts-list mid-pt other-verts-list parallel-search-dist)
      )
      (if near-pt
        (progn
          (setq to-near-x (- (car near-pt) (car mid-pt)))
          (setq to-near-y (- (cadr near-pt) (cadr mid-pt)))
          (setq side-dot (+ (* to-near-x perp-x) (* to-near-y perp-y)))
          (if (> side-dot 0.0)
            (setq perp-x (- perp-x)
                  perp-y (- perp-y))
          )
        )
        (if (> perp-y 0.0)
          (setq perp-x (- perp-x)
                perp-y (- perp-y))
        )
      )

      (setq dim-pt
        (list
          (+ (car mid-pt)  (* perp-x offset-dist))
          (+ (cadr mid-pt) (* perp-y offset-dist))
          0.0
        )
      )

      (if (not *VL:DIM-ON-LINE*) (setvar "DIMTAD" 4))
      (setq dim-obj
        (vl-catch-all-apply
          'vla-AddDimAligned
          (list mspace
                (vlax-3d-point pt1)
                (vlax-3d-point pt2)
                (vlax-3d-point dim-pt))
        )
      )

      (if (or (null dim-obj) (vl-catch-all-error-p dim-obj))
        (progn
          (princ "\n  ОШИБКА: не удалось создать параллельный размер.")
          nil
        )
        (progn
          (if dim-style-name
            (vl-catch-all-apply '(lambda () (vla-put-StyleName dim-obj dim-style-name)))
          )

          ;; --- Привязка: текст по центру линии, фон скрывает полилинию ---
          (if *VL:DIM-ON-LINE*
            (progn
              (vl-catch-all-apply '(lambda () (vla-put-VerticalTextPosition dim-obj 0)))
              (vl-catch-all-apply '(lambda () (vla-put-TextFill dim-obj :vlax-true)))
              (vl-catch-all-apply '(lambda () (vla-put-TextFillColor dim-obj 254)))
            )
          )

          ;; --- Оценка ширины текста ---
          (setq length-str     (vl:fmt-length seg-len))
          (setq char-count     (strlen length-str))
          (setq required-width (* char-count txt-height 0.6))

          (if (>= seg-len required-width)
            ;; --- Длинный сегмент: <> = живое значение AutoCAD ---
            (progn
              (vl-catch-all-apply '(lambda () (vla-put-TextOverride dim-obj "<>")))
              (setq label-ename (vlax-vla-object->ename dim-obj))
            )
            ;; --- Короткий сегмент: вынос (текст статичный) ---
            (progn
              (vl-catch-all-apply '(lambda () (vla-put-TextOverride dim-obj " ")))
              (setq label-ename
                (vl:create-mleader
                  mid-pt
                  (list (car mid-pt) (+ (cadr mid-pt) (* txt-height 2.0)) 0.0)
                  (list (+ (car mid-pt) (* txt-height 2.0))
                        (+ (cadr mid-pt) (* txt-height 2.0)) 0.0)
                  length-str
                  mleader-style-name
                  0.5
                  txt-height
                )
              )
              ;; маска 1.05 — только у текста выноски
              (if label-ename
                (vl:set-mleader-mask-scale label-ename 1.05)
              )
            )
          )
          label-ename
        )
      )
    )
  )
)

;;; ============================================================
;;; М-ЛИНИИ: поиск у полилинии и размер L=
;;; ============================================================

(defun vl:mline-verts (ename / obj coords verts n k pair)
  (setq verts '())
  (setq obj (vlax-ename->vla-object ename))
  (setq coords (vl-catch-all-apply 'vlax-get (list obj 'Coordinates)))
  (if (and (not (vl-catch-all-error-p coords))
           (listp coords)
           (numberp (car coords)))
    (progn
      (setq n (length coords) k 0)
      (while (< k n)
        (setq verts (cons (list (nth k coords) (nth (1+ k) coords) 0.0) verts))
        (setq k (+ k 3))
      )
      (setq verts (reverse verts))
    )
  )
  (if (or (null verts) (< (length verts) 2))
    (progn
      (setq verts '())
      (foreach pair (entget ename)
        (if (= (car pair) 11)
          (setq verts (cons (list (cadr pair) (caddr pair) 0.0) verts))
        )
      )
      (setq verts (reverse verts))
    )
  )
  verts
)

(defun vl:poly-len-2d (verts / i len)
  (setq len 0.0 i 0)
  (repeat (max 0 (1- (length verts)))
    (setq len (+ len (distance (nth i verts) (nth (1+ i) verts))))
    (setq i (1+ i))
  )
  len
)

(defun vl:dist-pt-poly-2d (pt verts / i va vb ax ay bx by px py abx aby ab2 param qx qy d mind)
  (setq mind 1e99 px (car pt) py (cadr pt) i 0)
  (repeat (max 0 (1- (length verts)))
    (setq va (nth i verts) vb (nth (1+ i) verts)
          ax (car va) ay (cadr va) bx (car vb) by (cadr vb)
          abx (- bx ax) aby (- by ay)
          ab2 (+ (* abx abx) (* aby aby)))
    (if (< ab2 1e-18)
      (setq d (distance pt va))
      (progn
        (setq param (/ (+ (* (- px ax) abx) (* (- py ay) aby)) ab2))
        (if (< param 0.0) (setq param 0.0))
        (if (> param 1.0) (setq param 1.0))
        (setq qx (+ ax (* param abx)) qy (+ ay (* param aby)))
        (setq d (distance pt (list qx qy 0.0)))
      )
    )
    (if (< d mind) (setq mind d))
    (setq i (1+ i))
  )
  mind
)

(defun vl:mline-near-segment-p (pt1 pt2 search-dist
                                 / ss-ml k ml-en ml-verts found mid-seg
                                   seg-dx seg-dy seg-len
                                   i va vb ml-dx ml-dy ml-seg-len
                                   d dotp len-diff)
  (setq found nil)
  (setq mid-seg (list (/ (+ (car pt1) (car pt2)) 2.0)
                       (/ (+ (cadr pt1) (cadr pt2)) 2.0)
                       0.0))
  (setq seg-dx (- (car pt2) (car pt1)))
  (setq seg-dy (- (cadr pt2) (cadr pt1)))
  (setq seg-len (sqrt (+ (* seg-dx seg-dx) (* seg-dy seg-dy))))

  (setq ss-ml (ssget "_X" '((0 . "MLINE"))))
  (if (and ss-ml (> seg-len 1e-9))
    (progn
      (setq k 0)
      (while (and (not found) (< k (sslength ss-ml)))
        (setq ml-en (ssname ss-ml k))
        (setq ml-verts (vl:mline-verts ml-en))
        (if (>= (length ml-verts) 2)
          (progn
            (setq i 0)
            (while (and (not found) (< i (1- (length ml-verts))))
              (setq va (nth i ml-verts)
                    vb (nth (1+ i) ml-verts)
                    ml-dx (- (car vb) (car va))
                    ml-dy (- (cadr vb) (cadr va))
                    ml-seg-len (distance va vb))
              (if (> ml-seg-len 1e-9)
                (progn
                  (setq d (vl:dist-pt-poly-2d mid-seg (list va vb)))
                  (setq dotp
                    (/ (abs (+ (* seg-dx ml-dx) (* seg-dy ml-dy)))
                       (* seg-len ml-seg-len)))
                  ;; близко + почти параллельно + почти та же длина
                  (if (and (<= d search-dist)
                           (>= dotp 0.9)
                           (<= (abs (- seg-len ml-seg-len)) 0.15))
                    (setq found T)
                  )
                )
              )
              (setq i (1+ i))
            )
          )
        )
        (setq k (1+ k))
      )
    )
  )
  found
)

(defun vl:nearest-seg-len-on-poly (pt verts / i va vb ax ay bx by px py abx aby ab2 param qx qy d mind best-len)
  (setq mind 1e99 best-len 0.0 px (car pt) py (cadr pt) i 0)
  (repeat (max 0 (1- (length verts)))
    (setq va (nth i verts) vb (nth (1+ i) verts)
          ax (car va) ay (cadr va) bx (car vb) by (cadr vb)
          abx (- bx ax) aby (- by ay)
          ab2 (+ (* abx abx) (* aby aby)))
    (if (< ab2 1e-18)
      (setq d (distance pt va))
      (progn
        (setq param (/ (+ (* (- px ax) abx) (* (- py ay) aby)) ab2))
        (if (< param 0.0) (setq param 0.0))
        (if (> param 1.0) (setq param 1.0))
        (setq qx (+ ax (* param abx)) qy (+ ay (* param aby)))
        (setq d (distance pt (list qx qy 0.0)))
      )
    )
    (if (< d mind) (progn (setq mind d) (setq best-len (distance va vb))))
    (setq i (1+ i))
  )
  best-len
)

;;; ------------------------------------------------------------
;;; Ближайшая точка на ОДНОЙ ломаной (список вершин) к точке pt.
;;; Возвращает точку (x y 0.0) либо nil, если verts пуст/вырожден.
;;; ------------------------------------------------------------
(defun vl:nearest-pt-on-verts (pt verts / i va vb ax ay bx by px py abx aby ab2 param qx qy d mind best)
  (setq mind 1e99 best nil px (car pt) py (cadr pt) i 0)
  (repeat (max 0 (1- (length verts)))
    (setq va (nth i verts) vb (nth (1+ i) verts)
          ax (car va) ay (cadr va) bx (car vb) by (cadr vb)
          abx (- bx ax) aby (- by ay)
          ab2 (+ (* abx abx) (* aby aby)))
    (if (< ab2 1e-18)
      (progn (setq qx ax qy ay) (setq d (distance pt va)))
      (progn
        (setq param (/ (+ (* (- px ax) abx) (* (- py ay) aby)) ab2))
        (if (< param 0.0) (setq param 0.0))
        (if (> param 1.0) (setq param 1.0))
        (setq qx (+ ax (* param abx)) qy (+ ay (* param aby)))
        (setq d (distance pt (list qx qy 0.0)))
      )
    )
    (if (< d mind) (progn (setq mind d) (setq best (list qx qy 0.0))))
    (setq i (1+ i))
  )
  best
)

;;; ------------------------------------------------------------
;;; Ближайшая точка среди СПИСКА ломаных (other-verts-list — список
;;; списков вершин) к точке pt, в пределах max-dist.
;;; Возвращает точку либо nil, если ничего не найдено в радиусе.
;;; ------------------------------------------------------------
(defun vl:nearest-pt-on-verts-list (pt verts-list max-dist / verts result best-d cand cd)
  (setq best-d max-dist result nil)
  (foreach verts verts-list
    (if (>= (length verts) 2)
      (progn
        (setq cand (vl:nearest-pt-on-verts pt verts))
        (if cand
          (progn
            (setq cd (distance pt cand))
            (if (< cd best-d) (progn (setq best-d cd) (setq result cand)))
          )
        )
      )
    )
  )
  result
)

(defun vl:add-mleader-simple (pt-arrow pt-text str txt-h style-name / mspace pts ml old-cmleaderstyle)
  (setq mspace (vla-get-ModelSpace
                 (vla-get-ActiveDocument (vlax-get-acad-object))))

  (setq old-cmleaderstyle (getvar "CMLEADERSTYLE"))
  (if (and style-name (vl:mleader-style-exists-p style-name))
    (vl-catch-all-apply 'setvar (list "CMLEADERSTYLE" style-name))
  )

  (setq pts (vlax-make-safearray vlax-vbDouble '(0 . 5)))
  (vlax-safearray-fill pts
    (list (car pt-arrow) (cadr pt-arrow) 0.0
          (car pt-text)  (cadr pt-text)  0.0))
  (setq ml (vl-catch-all-apply 'vla-AddMLeader (list mspace pts 0)))

  (setvar "CMLEADERSTYLE" old-cmleaderstyle)

  (if (vl-catch-all-error-p ml)
    nil
    (progn
      (vl-catch-all-apply '(lambda () (vla-put-StyleName ml style-name)))
      
      ;; точка на первой строке
      (vl-catch-all-apply '(lambda () (vla-put-TextString ml (strcat "." "\\P" str))))
      (vl-catch-all-apply '(lambda () (vla-put-TextHeight ml txt-h)))
      
      (vl-catch-all-apply '(lambda () (vla-put-EnableDogleg ml :vlax-true)))
      (vl-catch-all-apply '(lambda () (vla-put-ArrowheadType ml 20)))
      
      ;; горизонтальное + подчёркивание первой строки
      (vl-catch-all-apply '(lambda () (vla-put-TextAttachmentDirection ml 0)))
      (vl-catch-all-apply '(lambda () (vla-put-TextLeftAttachmentType  ml 3)))
      (vl-catch-all-apply '(lambda () (vla-put-TextRightAttachmentType ml 3)))
      (vl-catch-all-apply '(lambda () (vla-put-LandingGap ml 0.0)))
      
      ;; важно: отключаем автоматическое удлинение полки до текста
      (vl-catch-all-apply '(lambda () (vla-put-ExtendLeaderToText ml :vlax-false)))
      
      ;; маска фона
      (vl-catch-all-apply '(lambda () (vla-put-TextBackgroundFill ml :vlax-true)))
      (vl-catch-all-apply '(lambda () (vla-put-TextBackgroundColor ml 254)))
      (vl-catch-all-apply '(lambda () (vla-put-TextBackgroundScaleFactor ml 1.05)))
      (vl:set-mleader-mask-scale (vlax-vla-object->ename ml) 1.05)
      
      ;; ? САМОЕ ВАЖНОЕ: длину полки ставим в самом конце
      (vl-catch-all-apply '(lambda () (vla-put-DoglegLength ml 0.5)))
      
      ml
    )
  )
)


;;; --- Размеры всех М-линий рядом с полилинией ---
(defun vl:dim-mlines-near-polyline
       (pl-ename pl-verts search-dist txt-h dim-style-name mleader-style-name
                 mline-prefix already-dimmed
        / ss-ml j ml-en ml-verts d found-list
          mspace dim-obj txt need-w off
          i p1 p2 mid-ml len
          dx dy seg-len2 perp-x perp-y near-pt to-near-x to-near-y side-dot dim-pt txt-assoc)

  (setq found-list '())
  (setq search-dist (if search-dist search-dist 5.0))
  (setq txt-h (if txt-h txt-h 1.0))
  (setq off 2.0)
  (if (null mline-prefix) (setq mline-prefix "L="))

  (setq ss-ml (ssget "_X" '((0 . "MLINE"))))
  (if (null ss-ml)
    (princ "\n  MLINE не найдены.")
    (progn
      (setq j 0)
      (repeat (sslength ss-ml)
        (setq ml-en (ssname ss-ml j))
        (if (not (member ml-en already-dimmed))
          (progn
            (setq ml-verts (vl:mline-verts ml-en))
            (if (>= (length ml-verts) 2)
              (progn
                ;; проверяем, есть ли хотя бы одна вершина MLINE рядом с полилинией
                (setq d 1e99)
                (foreach p ml-verts
                  (setq d (min d (vl:dist-pt-poly-2d p pl-verts)))
                )
                (if (<= d search-dist)
                  (setq found-list (cons (list ml-en ml-verts) found-list))
                )
              )
            )
          )
        )
        (setq j (1+ j))
      )

      (if (null found-list)
        (princ (strcat "\n  Нет MLINE в пределах " (rtos search-dist 2 1) "."))
        (progn
          (setq mspace (vla-get-ModelSpace
                         (vla-get-ActiveDocument (vlax-get-acad-object))))
          (princ (strcat "\n  Обрабатываю MLINE: " (itoa (length found-list))))

          (foreach item found-list
            (setq ml-en    (car item)
                  ml-verts (cadr item))

            (setq already-dimmed (cons ml-en already-dimmed))

            ;; === ГЛАВНОЕ ИЗМЕНЕНИЕ: цикл по КАЖДОМУ сегменту MLINE ===
            (setq i 0)
            (repeat (1- (length ml-verts))
              (setq p1  (nth i ml-verts)
                    p2  (nth (1+ i) ml-verts)
                    len (distance p1 p2)
                    mid-ml (list (/ (+ (car p1) (car p2)) 2.0)
                                 (/ (+ (cadr p1) (cadr p2)) 2.0)
                                 0.0)
                    txt (strcat mline-prefix (vl:fmt-length len))
                    need-w (* (strlen txt) txt-h 0.6)
                    ;; associative override: L=<>  (updates when moved)
                    txt-assoc (strcat mline-prefix "<>"))

              ;; ставим размер только если сегмент действительно рядом с полилинией
              (if (<= (vl:dist-pt-poly-2d mid-ml pl-verts) search-dist)
                (progn
                  (setq dx (- (car p2) (car p1)))
                  (setq dy (- (cadr p2) (cadr p1)))
                  (setq seg-len2 (distance p1 p2))
                  (if (> seg-len2 1e-9)
                    (setq perp-x (/ (- dy) seg-len2) perp-y (/ dx seg-len2))
                    (setq perp-x 0.0 perp-y -1.0)
                  )

                  ;; выбираем сторону (от полилинии)
                  (setq near-pt (vl:nearest-pt-on-verts mid-ml pl-verts))
                  (if near-pt
                    (progn
                      (setq to-near-x (- (car near-pt) (car mid-ml)))
                      (setq to-near-y (- (cadr near-pt) (cadr mid-ml)))
                      (setq side-dot (+ (* to-near-x perp-x) (* to-near-y perp-y)))
                      (if (> side-dot 0.0)
                        (progn (setq perp-x (- perp-x)) (setq perp-y (- perp-y)))
                      )
                    )
                  )

                  (setq dim-pt
                    (list
                      (+ (car mid-ml) (* perp-x off))
                      (+ (cadr mid-ml) (* perp-y off))
                      0.0
                    )
                  )

                  ;; pered sozdaniem - DIMTAD=4 (pod liniey)
                  (setvar "DIMTAD" 4)
                  (setq dim-obj
                    (vla-AddDimAligned
                      mspace
                      (vlax-3d-point p1)
                      (vlax-3d-point p2)
                      (vlax-3d-point dim-pt)
                    )
                  )
                  (if dim-obj
                    (progn
                      (if dim-style-name
                        (vl-catch-all-apply
                          '(lambda () (vla-put-StyleName dim-obj dim-style-name)))
                      )
                      ;; prefix tolko cherez TextOverride (L=<> ili L-<>)
                      (if (>= len need-w)
                        (vl-catch-all-apply
                          '(lambda () (vla-put-TextOverride dim-obj txt-assoc)))
                        (progn
                          (vl-catch-all-apply
                            '(lambda () (vla-put-TextOverride dim-obj " ")))
                          (vl:add-mleader-simple
                            mid-ml
                            (list (+ (car mid-ml) (* perp-x txt-h 3.0))
                                  (+ (cadr mid-ml) (* perp-y txt-h 3.0))
                                  0.0)
                            txt
                            txt-h
                            mleader-style-name
                          )
                        )
                      )
                    )
                  )
                )
              )
              (setq i (1+ i))
            )
          )
        )
      )
    )
  )
  already-dimmed
)
;;; ============================================================
;;; ГЛАВНАЯ КОМАНДА: COORD
;;; ============================================================

;;; ============================================================
;;; Диалог настроек COORD (меньше кликов): одно окно вместо
;;; серии getkword. Запоминает последние значения в *VL:SETTINGS*.
;;; Возвращает assoc-список или nil при отмене.
;;; ============================================================
(defun vl:settings-get (key default / v)
  (setq v (if *VL:SETTINGS* (cdr (assoc key *VL:SETTINGS*)) nil))
  (if v v default)
)

(defun vl:settings-put (key val)
  (setq *VL:SETTINGS*
    (cons (cons key val)
          (vl-remove-if '(lambda (x) (= (car x) key)) *VL:SETTINGS*)))
)

(defun vl:settings-dialog (priv template-path def-dim def-mline
                           / names i-dim i-mline dclpath f id res
                             number-mode dim-mode mline-prefix output-mode
                             num-choice start-num continue-mode
                             do-export export-fmt only-export
                             has-continue cont-label
                             tile-num tile-dim tile-pref tile-out
                             tile-numch tile-start tile-cont
                             tile-ds1 tile-ds2 tile-exp tile-efmt
                             result)

  (setq names (vl:template-dimstyle-names template-path))
  (if (null names) (setq names (list "Standard")))

  ;; значения по умолчанию из прошлого запуска
  (setq number-mode   (vl:settings-get 'number-mode   (if priv "Нет" "Да")))
  (setq dim-mode      (vl:settings-get 'dim-mode      "Да"))
  (setq mline-prefix  (vl:settings-get 'mline-prefix  "L="))
  (setq output-mode   (vl:settings-get 'output-mode   "Мультивыноска"))
  (setq num-choice    (vl:settings-get 'num-choice    "Авто"))
  (setq start-num     (vl:settings-get 'start-num     "1"))
  (setq continue-mode (vl:settings-get 'continue-mode "Продолжить"))
  (setq do-export     (vl:settings-get 'do-export     "0"))
  (setq export-fmt    (vl:settings-get 'export-fmt    "Excel"))
  (setq only-export   (vl:settings-get 'only-export   "0"))

  (if priv (setq number-mode "Нет" dim-mode "Да"))

  ;; стили: из прошлого выбора или defaults
  (if *VL:DIM-CHOICE*
    (setq def-dim (car *VL:DIM-CHOICE*) def-mline (cadr *VL:DIM-CHOICE*))
  )
  (if (and priv *VL:PRIV-DIM-CHOICE*)
    (setq def-dim *VL:PRIV-DIM-CHOICE*)
  )
  (setq def-dim   (vl:settings-get 'dim-style       def-dim))
  (setq def-mline (vl:settings-get 'mline-dim-style def-mline))
  (setq i-dim   (vl:index-of-ci def-dim names))
  (setq i-mline (vl:index-of-ci def-mline names))

  (setq has-continue
    (and *VL:LAST-VERTEX-NUM* (> *VL:LAST-VERTEX-NUM* 0))
  )
  (setq cont-label
    (if has-continue
      (strcat "Продолжить с №" (itoa (1+ *VL:LAST-VERTEX-NUM*)) " / Заново")
      ""
    )
  )

  (setq dclpath (strcat (getenv "TEMP") "\\vl_coord_settings.dcl"))
  (setq f (open dclpath "w"))
  (write-line "vl_coord_settings : dialog {" f)
  (write-line (if priv
                "  label = \"ПРИВЯЗКА — настройки\";"
                "  label = \"COORD — настройки\";") f)
  (write-line "  spacer;" f)

  ;; --- Только экспорт ---
  (write-line "  : toggle { key = \"onlyexp\"; label = \"Только экспорт (без простановки номеров и размеров)\"; }" f)
  (write-line "  spacer;" f)

  ;; --- Номера / размеры ---
  (if (not priv)
    (progn
      (write-line "  : toggle { key = \"num\"; label = \"Проставлять номера вершин\"; }" f)
      (write-line "  : toggle { key = \"dim\"; label = \"Проставлять размеры сторон\"; }" f)
    )
    (write-line "  : text { label = \"Режим привязки: координаты + размеры (без номеров)\"; }" f)
  )

  (write-line "  spacer;" f)
  (write-line "  : popup_list { key = \"out\"; label = \"Способ вывода координат:\"; edit_width = 28; }" f)

  (if (not priv)
    (progn
      (write-line "  : popup_list { key = \"pref\"; label = \"Префикс длины М-линий:\"; edit_width = 12; }" f)
      (write-line "  spacer;" f)
      (write-line "  : popup_list { key = \"numch\"; label = \"Нумерация вершин:\"; edit_width = 28; }" f)
      (write-line "  : edit_box { key = \"start\"; label = \"Начальный номер:\"; edit_width = 8; }" f)
      (if has-continue
        (write-line (strcat "  : popup_list { key = \"cont\"; label = \"" cont-label ":\"; edit_width = 20; }") f)
      )
    )
  )

  (write-line "  spacer;" f)
  (write-line "  : popup_list { key = \"ds1\"; label = \"Стиль размеров сторон:\"; edit_width = 32; }" f)
  (if (not priv)
    (write-line "  : popup_list { key = \"ds2\"; label = \"Стиль размеров М-линий:\"; edit_width = 32; }" f)
  )

  (write-line "  spacer;" f)
  (write-line "  : toggle { key = \"exp\"; label = \"Экспортировать таблицу координат\"; }" f)
  (write-line "  : popup_list { key = \"efmt\"; label = \"Формат экспорта:\"; edit_width = 16; }" f)

  (write-line "  spacer;" f)
  (write-line "  ok_cancel;" f)
  (write-line "}" f)
  (close f)

  (setq id (load_dialog dclpath))
  (setq result nil)
  (cond
    ((and (> id 0) (new_dialog "vl_coord_settings" id))
     ;; --- заполнение списков ---
     (if (not priv)
       (progn
         (set_tile "num" (if (= number-mode "Да") "1" "0"))
         (set_tile "dim" (if (= dim-mode "Да") "1" "0"))
         (start_list "pref")
         (mapcar 'add_list (list "L=" "L-"))
         (end_list)
         (set_tile "pref" (if (= mline-prefix "L-") "1" "0"))
         (start_list "numch")
         (mapcar 'add_list (list "Авто" "Начальный номер точки"))
         (end_list)
         (set_tile "numch" (if (= num-choice "Начальный номер точки") "1" "0"))
         (set_tile "start" (if start-num start-num "1"))
         (if has-continue
           (progn
             (start_list "cont")
             (mapcar 'add_list (list "Продолжить" "Заново"))
             (end_list)
             (set_tile "cont" (if (= continue-mode "Заново") "1" "0"))
           )
         )
       )
     )

     (start_list "out")
     (mapcar 'add_list (list "Мультивыноска" "Блок"))
     (end_list)
     (set_tile "out" (if (= output-mode "Блок") "1" "0"))

     (start_list "ds1") (mapcar 'add_list names) (end_list)
     (set_tile "ds1" (itoa i-dim))
     (if (not priv)
       (progn
         (start_list "ds2") (mapcar 'add_list names) (end_list)
         (set_tile "ds2" (itoa i-mline))
       )
     )

     (set_tile "onlyexp" (if (= only-export "1") "1" "0"))
     (set_tile "exp" (if (= do-export "1") "1" "0"))
     (start_list "efmt")
     (mapcar 'add_list (list "Excel" "Word" "Оба"))
     (end_list)
     (set_tile "efmt"
       (cond ((= export-fmt "Word") "1")
             ((= export-fmt "Оба") "2")
             (T "0")))

     (action_tile "accept"
       (strcat
         "(progn"
         (if (not priv)
           (strcat
             " (setq number-mode (if (= (get_tile \"num\") \"1\") \"Да\" \"Нет\"))"
             " (setq dim-mode (if (= (get_tile \"dim\") \"1\") \"Да\" \"Нет\"))"
             " (setq mline-prefix (nth (atoi (get_tile \"pref\")) (list \"L=\" \"L-\")))"
             " (setq num-choice (nth (atoi (get_tile \"numch\")) (list \"Авто\" \"Начальный номер точки\")))"
             " (setq start-num (get_tile \"start\"))"
             (if has-continue
               " (setq continue-mode (nth (atoi (get_tile \"cont\")) (list \"Продолжить\" \"Заново\")))"
               " (setq continue-mode \"Продолжить\")"
             )
           )
           " (setq number-mode \"Нет\" dim-mode \"Да\" mline-prefix \"L=\" num-choice \"Авто\" start-num \"1\" continue-mode \"Продолжить\")"
         )
         " (setq output-mode (nth (atoi (get_tile \"out\")) (list \"Мультивыноска\" \"Блок\")))"
         " (setq i-dim (atoi (get_tile \"ds1\")))"
         (if (not priv)
           " (setq i-mline (atoi (get_tile \"ds2\")))"
           " (setq i-mline i-dim)"
         )
         " (setq only-export (get_tile \"onlyexp\"))"
         " (setq do-export (get_tile \"exp\"))"
         " (setq export-fmt (nth (atoi (get_tile \"efmt\")) (list \"Excel\" \"Word\" \"Оба\")))"
         " (done_dialog 1))"
       )
     )
     (action_tile "cancel" "(done_dialog 0)")
     (setq res (start_dialog))
     (unload_dialog id)
     (vl-file-delete dclpath)

     (if (= res 1)
       (progn
         (vl:settings-put 'number-mode   number-mode)
         (vl:settings-put 'dim-mode      dim-mode)
         (vl:settings-put 'mline-prefix  mline-prefix)
         (vl:settings-put 'output-mode   output-mode)
         (vl:settings-put 'num-choice    num-choice)
         (vl:settings-put 'start-num     start-num)
         (vl:settings-put 'continue-mode continue-mode)
         (vl:settings-put 'dim-style     (nth i-dim names))
         (vl:settings-put 'mline-dim-style (nth i-mline names))
         (vl:settings-put 'do-export     do-export)
         (vl:settings-put 'export-fmt    export-fmt)
         (vl:settings-put 'only-export   only-export)
         (if priv
           (setq *VL:PRIV-DIM-CHOICE* (nth i-dim names))
           (setq *VL:DIM-CHOICE* (list (nth i-dim names) (nth i-mline names)))
         )
         (setq result
           (list
             (cons 'number-mode   number-mode)
             (cons 'dim-mode      dim-mode)
             (cons 'mline-prefix  mline-prefix)
             (cons 'output-mode   output-mode)
             (cons 'num-choice    num-choice)
             (cons 'start-num     start-num)
             (cons 'continue-mode continue-mode)
             (cons 'dim-style     (nth i-dim names))
             (cons 'mline-dim-style (nth i-mline names))
             (cons 'do-export     do-export)
             (cons 'export-fmt    export-fmt)
             (cons 'only-export   only-export)
           )
         )
       )
     )
    )
    (T
     (princ "\n  Не удалось открыть диалог настроек — использую значения по умолчанию.")
     (setq result
       (list
         (cons 'number-mode   (if priv "Нет" "Да"))
         (cons 'dim-mode      "Да")
         (cons 'mline-prefix  "L=")
         (cons 'output-mode   "Мультивыноска")
         (cons 'num-choice    "Авто")
         (cons 'start-num     "1")
         (cons 'continue-mode "Продолжить")
         (cons 'dim-style     def-dim)
         (cons 'mline-dim-style def-mline)
         (cons 'do-export     "0")
         (cons 'export-fmt    "Excel")
         (cons 'only-export   "0")
       )
     )
    )
  )
  result
)


;;; ------------------------------------------------------------
;;; Экранирование имени слоя для фильтра ssget
;;; (запятая, *, ? и прочие служебные символы).
;;; ------------------------------------------------------------
(defun vl:ss-escape (s / i c out)
  (setq out "" i 1)
  (repeat (strlen s)
    (setq c (substr s i 1))
    (if (member c '("`" "," "#" "." "@" "*" "?" "~" "[" "]"))
      (setq out (strcat out "`" c))
      (setq out (strcat out c))
    )
    (setq i (1+ i))
  )
  out
)

;;; Все полилинии модели на том же слое, что и образец.
(defun vl:similar-polys-on-layer (seed / ed lay ss)
  (setq ed (entget seed))
  (if (null ed)
    nil
    (progn
      (setq lay (cdr (assoc 8 ed)))
      (setq ss
        (ssget "_X"
          (list
            '(0 . "LWPOLYLINE,POLYLINE,3DPOLYLINE")
            '(410 . "Model")
            (cons 8 (vl:ss-escape lay))
          )
        )
      )
      (if (null ss)
        (progn
          (setq ss (ssadd))
          (ssadd seed ss)
        )
        (if (not (ssmemb seed ss))
          (ssadd seed ss)
        )
      )
      ss
    )
  )
)

;;; Привязка: одна полилиния -> подобные на слое -> пользователь
;;; снимает лишние (Shift) и Enter. Если уже выделено несколько
;;; полилиний, берём их как есть.
(defun vl:priv-pick-similar (/ ss seed ed lay n)
  (setq ss (ssget "_I" '((0 . "LWPOLYLINE,POLYLINE,3DPOLYLINE"))))
  (cond
    ((and ss (> (sslength ss) 1))
     (princ (strcat "\n  Используется текущий выбор: " (itoa (sslength ss)) " полилиний."))
     ss
    )
    (T
     (if (and ss (= (sslength ss) 1))
       (setq seed (ssname ss 0))
       (progn
         (princ "\n  Укажите одну полилинию — будут найдены подобные на том же слое.")
         (setq seed (car (entsel "\nПолилиния: ")))
       )
     )
     (if (or (null seed) (null (entget seed)))
       nil
       (progn
         (setq ed (entget seed))
         (if (not (member (cdr (assoc 0 ed)) '("LWPOLYLINE" "POLYLINE" "3DPOLYLINE")))
           (progn
             (princ "\n  Указанный объект не является полилинией.")
             nil
           )
           (progn
             (setq lay (cdr (assoc 8 ed)))
             (setq ss (vl:similar-polys-on-layer seed))
             (setq n (if ss (sslength ss) 0))
             (princ
               (strcat
                 "\n  Слой «" lay "»: подобных полилиний — " (itoa n) "."
               )
             )
             (if (<= n 1)
               ss
               (progn
                 (princ "\n  Они выделены. Снимите лишние (Shift+клик) и нажмите Enter.")
                 (setq *VL:SAVED-PICKADD* (getvar "PICKADD"))
                 (setvar "PICKADD" 1)
                 (sssetfirst nil nil)
                 (command "_.SELECT" ss pause)
                 (while (= (logand (getvar "CMDACTIVE") 1) 1)
                   (command pause)
                 )
                 (setvar "PICKADD" *VL:SAVED-PICKADD*)
                 (setq *VL:SAVED-PICKADD* nil)
                 (sssetfirst nil nil)
                 (setq ss (ssget "_P" '((0 . "LWPOLYLINE,POLYLINE,3DPOLYLINE"))))
                 (if ss
                   (princ (strcat "\n  К обработке: " (itoa (sslength ss)) " полилиний."))
                 )
                 ss
               )
             )
           )
         )
       )
     )
    )
  )
)

(defun vl:coord-main (priv / last0 sel ename vertices pt-count idx pt
                          x-coord y-coord real-x real-y coord-text
                          label-w label-h vert-pos poly-closed
                          mleader-style-name text-style-name actual-mleader-style
                          template-path export-data
                          txt-height land-length
                          pt-land pt-text
                          ml-ename num-ename
                          num-text num-ins-pt
                          dim-offset dim-text-gap seg-count seg-idx seg-pt1 seg-pt2
                          dim-style-name actual-dim-style-name
                          old-osmode old-cmdecho start-choice old-error-handler
                          output-mode coord-block-name block-scale
                          number-mode dim-mode mline-prefix
                          all-sel-verts other-verts-list parallel-search-dist en pr
                          processed-pts already num-choice
                          ss ename-list sel-idx dimmed-mlines-list
                          actual-mline-dim-style-name mline-dim-style-name dim-pick
                          existing-pts skipped
                          settings do-export export-fmt base-path
                          continue-mode start-num only-export)


  (vl-load-com)
 
  (vl:reset-placement-index)
  (setq *VL:DIM-ON-LINE* priv)

  (setq mleader-style-name "Координаты")
  (setq text-style-name    "Д-431")
  (setq dim-style-name     "длина сети iso")
  (setq mline-dim-style-name "Длина трубы iso")
  (setq coord-block-name "XY")

  (setq block-scale 1.0)

  (setq template-path *VL:TEMPLATE-PATH*)

  (setq old-osmode  (getvar "OSMODE"))
  (setq old-cmdecho (getvar "CMDECHO"))
  (setvar "CMDECHO" 0)
  (setvar "OSMODE"  0)

  (setq old-error-handler *error*)
  (defun *error* (msg)
    (setvar "OSMODE"  old-osmode)
    (setvar "CMDECHO" old-cmdecho)
    (if (and (boundp '*VL:SAVED-PICKADD*) (numberp *VL:SAVED-PICKADD*))
      (setvar "PICKADD" *VL:SAVED-PICKADD*)
    )
    (setq *VL:SAVED-PICKADD* nil)
    (setq *error* old-error-handler)
    (if (not (wcmatch (strcase msg) "*CANCEL*,*EXIT*,*QUIT*"))
      (princ (strcat "\n  ОШИБКА: " msg))
    )
    (princ "\n  Команда отменена.")
    (princ)
  )

  (if priv
    (princ "\n=== Привязка: координаты и размеры по полилинии ===")
    (princ "\n=== Простановка координатных выносок и размеров по полилинии ===")
  )

  (vl:ensure-text-style text-style-name)

  (if (vl:ensure-mleader-style-from-template template-path mleader-style-name)
    (setq actual-mleader-style mleader-style-name)
    (progn
      (princ "\n  Использую «Standard» как базу — параметры оформления")
      (princ "\n  назначаются вручную каждому объекту.")
      (setq actual-mleader-style "Standard")
    )
  )

  ;; --- Выбор полилиний ---
  ;; Привязка: клик по одной -> подобные на слое, лишние снимаются.
  ;; COORD: прежний множественный выбор (или уже выделенные).
  (if priv
    (setq ss (vl:priv-pick-similar))
    (progn
      (setq ss (ssget "_I" '((0 . "LWPOLYLINE,POLYLINE,3DPOLYLINE"))))
      (if ss
        (princ (strcat "\n  Используется текущий выбор: " (itoa (sslength ss)) " объект(ов)."))
        (progn
          (princ "\n  Выберите нужные полилинии (можно несколько).")
          (princ "\n  Когда все нужные объекты выбраны — нажмите ENTER, чтобы завершить выбор.")
          (setq ss (ssget '((0 . "LWPOLYLINE,POLYLINE,3DPOLYLINE"))))
        )
      )
    )
  )

  (if (null ss)
    (progn
      (princ "\n  Выбор отменён, либо не выбрано ни одной полилинии.")
      (princ)
      (exit)
    )
  )

  (setq ename-list '())
  (setq sel-idx 0)
  (repeat (sslength ss)
    (setq ename-list (append ename-list (list (ssname ss sel-idx))))
    (setq sel-idx (1+ sel-idx))
  )

  (princ (strcat "\n  Выбрано полилиний: " (itoa (length ename-list))))

  (if (and *VL:LAST-POLY-ENAME* (not (entget *VL:LAST-POLY-ENAME*)))
    (progn
      (setq *VL:LAST-VERTEX-NUM* nil)
      (setq *VL:COORD-MASTER-PT* nil)
      (setq *VL:ALL-EXPORT-DATA* '())
      (princ "\n Предыдущая полилиния была удалена. Счетчик сброшен.")
    )
  )

  ;; --- Одно окно настроек вместо серии getkword ---
  (setq dim-style-name     "длина сети iso")
  (setq mline-dim-style-name "Длина трубы iso")
  (setq settings
    (vl:settings-dialog
      priv
      template-path
      (if priv "Привязки" dim-style-name)
      mline-dim-style-name
    )
  )
  (if (null settings)
    (progn
      (princ "\n  Настройки отменены.")
      (exit)
    )
  )

  (setq number-mode   (cdr (assoc 'number-mode settings)))
  (setq dim-mode      (cdr (assoc 'dim-mode settings)))
  (setq mline-prefix  (cdr (assoc 'mline-prefix settings)))
  (setq output-mode   (cdr (assoc 'output-mode settings)))
  (setq num-choice    (cdr (assoc 'num-choice settings)))
  (setq start-num     (cdr (assoc 'start-num settings)))
  (setq continue-mode (cdr (assoc 'continue-mode settings)))
  (setq do-export     (cdr (assoc 'do-export settings)))
  (setq export-fmt    (cdr (assoc 'export-fmt settings)))
  (setq only-export   (cdr (assoc 'only-export settings)))
  (setq dim-style-name       (cdr (assoc 'dim-style settings)))
  (setq mline-dim-style-name (cdr (assoc 'mline-dim-style settings)))

  (if (null number-mode) (setq number-mode (if priv "Нет" "Да")))
  (if (null dim-mode) (setq dim-mode "Да"))
  (if (null mline-prefix) (setq mline-prefix "L="))
  (if (null output-mode) (setq output-mode "Мультивыноска"))
  (if (null num-choice) (setq num-choice "Авто"))
  (if (null do-export) (setq do-export "0"))
  (if (null export-fmt) (setq export-fmt "Excel"))
  (if (null only-export) (setq only-export "0"))

  ;; Если включён «Только экспорт» — отключаем простановку
  (if (= only-export "1")
    (progn
      (setq number-mode "Нет")
      (setq dim-mode    "Нет")
      (setq do-export   "1")
      ;; чистая таблица только по текущему выбору
      (setq *VL:ALL-EXPORT-DATA* '())
      (setq idx 1)
      (princ "\n  Режим: ТОЛЬКО ЭКСПОРТ (номера и размеры не ставятся).")
    )
  )

  ;; --- Подготовка размерных стилей ---
  (if (= dim-mode "Да")
    (progn
      (if (vl:ensure-dimstyle-from-template template-path dim-style-name)
        (setq actual-dim-style-name dim-style-name)
        (progn
          (princ "\n  Использую «Standard» как базовый размерный стиль.")
          (setq actual-dim-style-name "Standard")
        )
      )
      (if (not priv) (vl:force-dimstyle-text-below actual-dim-style-name))

      (if (vl:ensure-dimstyle-from-template template-path mline-dim-style-name)
        (setq actual-mline-dim-style-name mline-dim-style-name)
        (progn
          (princ "\n  Использую «Standard» как стиль размеров М-линий.")
          (setq actual-mline-dim-style-name "Standard")
        )
      )
      (if (not priv) (vl:force-dimstyle-text-below actual-mline-dim-style-name))
    )
    (progn
      (setq actual-dim-style-name       "Standard")
      (setq actual-mline-dim-style-name "Standard")
    )
  )

  (if (= output-mode "Блок")
    (vl:ensure-coord-block-from-template template-path coord-block-name)
  )

  ;; --- Нумерация ---
  (if (= number-mode "Нет")
    (setq idx 1)
    (progn
      (if (= num-choice "Начальный номер точки")
        (progn
          (setq idx (atoi (if start-num start-num "1")))
          (if (< idx 1) (setq idx 1))
        )
        ;; Авто
        (if (and *VL:LAST-VERTEX-NUM* (> *VL:LAST-VERTEX-NUM* 0))
          (if (or (null continue-mode) (= continue-mode "Продолжить"))
            (setq idx (1+ *VL:LAST-VERTEX-NUM*))
            (progn
              (setq idx 1)
              (setq *VL:ALL-EXPORT-DATA* nil)
            )
          )
          (setq idx 1)
        )
      )
    )
  )
  (princ (strcat "\n  Нумерация вершин начнётся с №" (itoa idx) "."))

  ;; --- Параметры оформления ---
  (setq txt-height  0.9)
  (setq land-length (* txt-height 1.5))
  (setq dim-offset    (if priv 0.0 1.0))
  (setq dim-text-gap  0.5)
  (setq parallel-search-dist 10.0)

  (setq export-data '())
  (setq processed-pts '())
  (setq existing-pts (vl:collect-existing-coord-pts coord-block-name))
  (setq dimmed-mlines-list '())

  ;; --- Собираем вершины всех выбранных полилиний ---
  (setq all-sel-verts '())
  (foreach en ename-list
    (setq all-sel-verts
      (append all-sel-verts (list (cons en (vl:get-polyline-vertices en))))
    )
  )

  (foreach ename ename-list
    (progn
      (setq vertices (vl:get-polyline-vertices ename))

      (setq other-verts-list '())
      (foreach pr all-sel-verts
        (if (and (not (eq (car pr) ename)) (cdr pr))
          (setq other-verts-list (cons (cdr pr) other-verts-list))
        )
      )

      (if (null vertices)
        (princ "\n  ОШИБКА: не удалось извлечь вершины полилинии, пропускаю объект.")
        (progn
          (setq pt-count (length vertices))
          (princ (strcat "\n\n  --- Обработка полилинии (" (itoa pt-count) " верш.) ---"))

          ;; ============================================================
          ;; ЧАСТЬ 1: координатные выноски и номера
          ;; ============================================================
          (setq last0 (entlast))
          (setq seg-count (1- pt-count))
          (setq vert-pos 0)
          (setq poly-closed (vl:polyline-closed-p ename))

          (setq skipped 0)
          (foreach pt vertices
            (setq already nil)
            (foreach ppt processed-pts
              (if (and (not already) (< (distance pt ppt) 0.001))
                (setq already T)
              )
            )
            ;; вершина уже размечена при прошлом запуске — пропускаем простановку
            (if (and (not already) (vl:pt-in-list-p pt existing-pts 0.01))
              (progn
                (setq already T)
                (setq skipped (1+ skipped))
              )
            )

            ;; --- ВСЕГДА собираем координаты для экспорта ---
            (setq real-x (car pt))
            (setq real-y (cadr pt))
            (setq x-coord real-y)
            (setq y-coord real-x)

            (setq *VL:ALL-EXPORT-DATA*
              (append *VL:ALL-EXPORT-DATA*
                (list (list idx (vl:fmt-coord x-coord) (vl:fmt-coord y-coord)))
              )
            )

            ;; --- Простановка только если вершина новая и не режим «только экспорт» ---
            (if (and (not already) (/= only-export "1"))
              (progn
                (setq coord-text (strcat "X= " (vl:fmt-coord x-coord) "\\PY= " (vl:fmt-coord y-coord)))

                (setq label-w (vl:estimate-text-width (strcat "X= " (vl:fmt-coord x-coord)) txt-height))
                (setq label-w (max label-w (vl:estimate-text-width (strcat "Y= " (vl:fmt-coord y-coord)) txt-height)))
                (setq label-h (* txt-height 2.8))
                (setq pt-land
                  (vl:find-label-placement (list real-x real-y 0.0) label-w label-h vertices seg-count land-length vert-pos poly-closed)
                )
                (setq pt-text (list (+ (car pt-land) land-length) (cadr pt-land) 0.0))

                (if (= output-mode "Мультивыноска")
                  (vl:create-mleader (list real-x real-y 0.0) pt-land pt-text coord-text actual-mleader-style land-length txt-height)
                  (vl:insert-coord-block
                    (list real-x real-y 0.0)
                    coord-block-name
                    (vl:fmt-coord x-coord)
                    (vl:fmt-coord y-coord)
                    block-scale
                    txt-height
                    0.0
                  )
                )

                (if (= number-mode "Да")
                  (vl:create-mtext-masked (list real-x real-y 0.0) (itoa idx) txt-height 0.0 1 text-style-name)
                )

                (setq processed-pts (cons pt processed-pts))
              )
            )

            ;; номер увеличиваем всегда — таблица экспорта со сплошной нумерацией
            (setq idx (1+ idx))
            (setq vert-pos (1+ vert-pos))
          )

          (setq *VL:LAST-POLY-ENAME* ename)
          (if (> skipped 0)
            (princ (strcat "\n  Пропущено вершин с уже существующей меткой: " (itoa skipped)))
          )
          (setq *VL:LAST-VERTEX-NUM* (1- idx))

          ;; ============================================================
          ;; ЧАСТЬ 2: простановка размеров по сторонам полигона
          ;; ============================================================
          (if (= dim-mode "Да")
            (progn
              (setq seg-count (1- pt-count))
              (setq seg-idx 0)

              (repeat seg-count
                (if (or priv
                        (not (vl:mline-near-segment-p
                               (nth seg-idx vertices)
                               (nth (1+ seg-idx) vertices)
                               2.0)))
                  (vl:create-parallel-dim-with-label
                    (nth seg-idx vertices)
                    (nth (1+ seg-idx) vertices)
                    dim-offset
                    txt-height
                    actual-dim-style-name
                    actual-mleader-style
                    dim-text-gap
                    other-verts-list
                    parallel-search-dist
                  )
                )
                (setq seg-idx (1+ seg-idx))
              )

              (if (and (vl:polyline-closed-p ename)
                       (or priv
                           (not (vl:mline-near-segment-p
                                  (last vertices)
                                  (car vertices)
                                  5.0))))
                (vl:create-parallel-dim-with-label
                  (nth seg-idx vertices)
                  (nth (1+ seg-idx) vertices)
                  dim-offset
                  txt-height
                  actual-dim-style-name
                  actual-mleader-style
                  dim-text-gap
                  other-verts-list
                  parallel-search-dist
                )
              )
              (if (not priv)
                (setq dimmed-mlines-list
                  (vl:dim-mlines-near-polyline
                    ename
                    vertices
                    5.0
                    txt-height
                    actual-mline-dim-style-name
                    actual-mleader-style
                    mline-prefix
                    dimmed-mlines-list
                  )
                )
              )
            )
          )

          ;; --- Привязка: слой и цвет новых объектов - по полилинии ---
          (if priv (vl:apply-poly-props last0 ename))
        )
      )
    )
  )

  (setq *VL:DIM-ON-LINE* nil)
  ;; экспорт только если включён флажок в диалоге
  (if (and (= do-export "1") *VL:ALL-EXPORT-DATA*)
    (progn
      (setq base-path
        (getfiled "Укажите имя файла для экспорта" "координаты" "csv" 1)
      )
      (if (null base-path)
        (princ "\n  Экспорт отменён пользователем.")
        (progn
          (if (wcmatch (strcase base-path) "*.CSV")
            (setq base-path (substr base-path 1 (- (strlen base-path) 4)))
          )
          (cond
            ((= export-fmt "Excel")
             (vl:export-csv *VL:ALL-EXPORT-DATA* (strcat base-path ".csv"))
            )
            ((= export-fmt "Word")
             (vl:export-rtf *VL:ALL-EXPORT-DATA* (strcat base-path ".rtf"))
            )
            ((= export-fmt "Оба")
             (vl:export-csv *VL:ALL-EXPORT-DATA* (strcat base-path ".csv"))
             (vl:export-rtf *VL:ALL-EXPORT-DATA* (strcat base-path ".rtf"))
            )
          )
        )
      )
    )
    (if (= do-export "1")
      (princ "\n  Нет данных для экспорта.")
      (princ "\n  Экспорт пропущен (флажок выключен).")
    )
  )

  (setvar "OSMODE" old-osmode)
  (setvar "CMDECHO" old-cmdecho)
  (setq *error* old-error-handler)

  (command "_.REGEN")
  (if priv
    (princ "\n=== Привязка завершена ===")
    (princ "\n=== COORD завершена ===")
  )
  (princ)
)

;;; ============================================================
;;; Алиасы команды COORD: CCL, ВЫНОСКА
;;; ============================================================
(defun c:COORD () (vl:coord-main nil))
(defun c:CCL () (c:COORD))
(defun c:КООРД () (c:COORD))
(defun c:КОО () (c:COORD))

;;; ============================================================
;;; Команда ПРИВЯЗКА (PRIVYAZKA, PRV): без номеров вершин;
;;; координаты + размеры по полилинии; слой и цвет - как у полилинии
;;; ============================================================
(defun c:PRIVYAZKA () (vl:coord-main T))
(defun c:PRV () (vl:coord-main T))
(defun c:ПРИВЯЗКА () (vl:coord-main T))
(defun c:ПРИВ () (vl:coord-main T))


;;; ============================================================
;;; ДОПОЛНИТЕЛЬНАЯ УТИЛИТА: RESETVERTEXNUM
;;; ============================================================
(defun c:RESETVERTEXNUM ()
  (setq *VL:LAST-VERTEX-NUM* nil)
  (setq *VL:ALL-EXPORT-DATA* '())
  (setq *VL:LAST-POLY-ENAME* nil)
  (vl:reset-placement-index)
  (setq *VL:COORD-MASTER-ENAME* nil)
  (setq *VL:COORD-MASTER-PT* nil)
  (princ "\nСброс, следующий вызов начнёт нумерацию точек как для первого запуска.")
  (princ)
)


;;; ============================================================
;;; ДОПОЛНИТЕЛЬНАЯ УТИЛИТА: CHECKSTYLE
;;; ============================================================
(defun c:CHECKSTYLE (/ mleader-style-name text-style-name template-path)
  (setq mleader-style-name "Координаты")
  (setq text-style-name    "Д-431")
  (setq template-path *VL:TEMPLATE-PATH*)

  (vl-load-com)
  (vl:ensure-text-style text-style-name)
  (vl:ensure-mleader-style-from-template template-path mleader-style-name)
  (princ)
)


(defun c:MTTEST (/ e)
  (if (setq e (car (entsel "\nВыберите MText: ")))
    (progn
      (setq e (entget e '("*")))
      (foreach x e
        (print x)
      )
    )
  )
  (princ)
)


(princ "\nCOORD.lsp загружен. Команды: COORD / CCL / КООРД / КОО.")
(princ)
